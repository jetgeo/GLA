FME workspace QUADRIgml2none.fmw

Parameters:
- SourceDataset_GML = C:\DATA\GLA\Data\1902\20170131\*.gml   # Source Geography Markup Language (GML) File(s)
- DestDataset_TEXTLINE_3 = C:\DATA\GLA\Data\1902\20170131\Belysningspunkt.xml   # Destination Text File
- DakatVersjon = 2.07   # Datakatalogversjon

Readers:
- GML_1: GML from $(SourceDataset_GML)

Writers:
- TEXTLINE_1: TEXTLINE to $(DestDataset_TEXTLINE_3)

Belysningsstrekning (reader GML_1)
    attributes: OBJTYPE xml_char(32), NVDB_BRUKSOMRÅDE xml_char(5), ENDRINGSFLAGG.ENDRET_TYPE xml_char(1), ENDRINGSFLAGG.ENDRET_TID xml_char(20), NVDB_TYPE xml_char(5), NVDB_FJERNSTYRING xml_char(4), GEOMETRITYPE xml_char(4), NVDB_EIER xml_char(4), NVDB_VEDLIKEHOLDSANSVARLIG xml_char(4), NVDB_EIERNAVN xml_char(5), DATAFANGSTDATO xml_char(20), OPPDATERINGSDATO xml_char(20), KVALITET.MÅLEMETODE xml_int16, KVALITET.SYNBARHET xml_int16, KOMM xml_char(4), LTEMA xml_char(4), gml_curveProperty xml_geometry, gml_multiCurveProperty xml_geometry
    -> Matcher
Lysarmatur (reader GML_1)
    attributes: DATAFANGSTDATO xml_char(20), OBJTYPE xml_char(32), OPPDATERINGSDATO xml_char(20), ENDRINGSFLAGG.ENDRET_TYPE xml_char(1), ENDRINGSFLAGG.ENDRET_TID xml_char(20), NVDB_ANTALLARMATURERIBELYSNINGSPKT xml_char(4), NVDB_LYSKILDETYPE xml_char(5), NVDB_EFFEKT xml_char(4), NVDB_ANTALLLYSKILDERPERARMATUR xml_char(4), KVALITET.MÅLEMETODE xml_int16, KVALITET.SYNBARHET xml_int16, NVDB_VEDLIKEHOLDSANSVARLIG xml_char(4), NVDB_EIER xml_char(4), GEOMETRITYPE xml_char(4), PTEMA xml_char(4), KOMM xml_char(4), NVDB_DRIFTSATTÅR xml_char(4), NVDB_EIERNAVN xml_char(5), NVDB_PRODUKTNAVNARMATUR xml_char(5), NVDB_PRODUSENTNAVNARMATUR xml_char(4), gml_pointProperty xml_geometry, gml_multiPointProperty xml_geometry
    -> Matcher
Belysningspunkt (reader GML_1)
    attributes: OBJTYPE xml_char(32), ENDRINGSFLAGG.ENDRET_TYPE xml_char(1), ENDRINGSFLAGG.ENDRET_TID xml_char(20), NVDB_BRUKSOMRÅDE xml_char(5), NVDB_PLASSERING xml_char(5), NVDB_STRØMTILFØRSELKATEGORI xml_char(4), NVDB_TILSTANDSKADEBELYSNING.NVDB_TILSTAND xml_char(4), GEOMETRITYPE xml_char(4), NVDB_EIER xml_char(4), NVDB_VEDLIKEHOLDSANSVARLIG xml_char(4), NVDB_EIERNAVN xml_char(5), NVDB_TILSTANDSKADEFUPUNKT.NVDB_ETTERSLEP xml_char(4), DATAFANGSTDATO xml_char(20), OPPDATERINGSDATO xml_char(20), KVALITET.MÅLEMETODE xml_int16, KVALITET.NØYAKTIGHET xml_int32, KVALITET.SYNBARHET xml_int16, PTEMA xml_char(4), KOMM xml_char(4), NVDB_ANTALL xml_char(4), NVDB_OVERBELASTNINGSVERN xml_char(4), gml_pointProperty xml_geometry, gml_multiPointProperty xml_geometry
    -> Matcher
Lysmast (reader GML_1)
    attributes: DATAFANGSTDATO xml_char(20), OBJTYPE xml_char(32), ENDRINGSFLAGG.ENDRET_TID xml_char(20), ENDRINGSFLAGG.ENDRET_TYPE xml_char(1), NVDB_TYPE xml_char(5), NVDB_VEDLIKEHOLDSANSVARLIG xml_char(4), NVDB_EIER xml_char(4), NVDB_BYGGEÅR xml_char(4), GEOMETRITYPE xml_char(4), KOMM xml_char(4), NVDB_TOTALMASTELENGDE xml_char(4), OPPDATERINGSDATO xml_char(20), KVALITET.MÅLEMETODE xml_int16, KVALITET.SYNBARHET xml_int16, HREF xml_char(6), PTEMA xml_char(4), NVDB_EIERNAVN xml_char(5), NVDB_FUNDAMENTERING xml_char(4), NVDB_PRODUKTNAVN xml_char(5), gml_pointProperty xml_geometry, gml_multiPointProperty xml_geometry
    -> Matcher
Matcher
    MATCH = 2D
    BLANK_AND_MISSING_DIFFER = No
    CNT_ATTR = _match_id
    LENIENT_MATCH = No
    MATCHATTRS = fme_feature_type
    MATCH_STRATEGY = Match Selected Attributes
    MATCHED -> Matcher_Matched
    SINGLE_MATCHED -> SchemaMapper
    NOT_MATCHED -> SchemaMapper
Matcher_Matched: Inspector
    TACKATTRS = fme_basename
Note: TempId
Counter
    DOMAIN = counter
    CNT_ATTR = tempId
    START = 1
    SCOPE = Global
    -> AttributeManager
    -> Counter_Output
Counter_Output: Inspector
    TACKATTRS = fme_feature_type
NullAttributeMapper
    OTHER_VALUE = 0
    SOURCE_ATTR_VAL = Null Empty "Missing (Selected Attributes Only)"
    NULL_TREATMENT = Missing
    ATTRCHOICE = All Attributes
    -> AttributeExploder
    -> FeatureMerger_5 [REQUESTOR]
    -> Kobla
Kobla: Inspector [off]
    TACKATTRS = fme_feature_type
Note: Kobler liste med egenskaper til objektet
FeatureMerger_5
    IGNORE_NULLS = No
    MERGE_TYPE = Attributes Only
    SUPPLIERS_FIRST = No
    PROCESS_DUPS = No
    ATTR_CONFLICT_RES = Use Requestor
    JOIN_KEYS = @Value(tempId) @Value(tempId) AUTO
    ATTR_ACCUM_MODE = Merge Supplier
    MERGED -> AttributeManager_12
Note: Tilpasninger på vegObjektnivå
AttributeManager_12
    ATTR_TABLE:
      SET_TO vegObjekt.typeId = @Value(fme_feature_type)
      SET_TO vegObjekt.tempId = FME_CONDITIONAL:DEFAULT_VALUE'_FME_NO_OP_'BOOL_OP;OR;COMPOSITE_TEST;<Unused>;TEST @Value(endringsflagg.Endringsflagg.typeEndring) = N'@Value(tempId)'FME_NUM_CONDITIONS2___
      SET_TO vegObjekt.nvdbId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
      SET_TO vegObjekt.versjon = FME_CONDITIONAL:DEFAULT_VALUE'_FME_NO_OP_'BOOL_OP;OR;COMPOSITE_TEST;<Unused>;TEST @Value(endringsflagg.Endringsflagg.typeEndring) = E'@Value(identifikasjon.Identifikasjon.versjonId)'FME_NUM_CONDITIONS2___
    -> vegObjektXML [ROOT]
vegObjektXML: XMLTemplater
    RESULT_ATTRIBUTE = vegObjekt.XML
    VISIBLE_QUERY_VALIDATE = Yes
    OUTPUT_XML_HEADER = No
    ROOT_QUERY_EXPR:
      {if( fme:has-attribute("vegObjekt.nvdbId")) then
          <vegObjekt typeId="{fme:get-attribute("vegObjekt.typeId")}" nvdbId="{fme:get-attribute("vegObjekt.nvdbId")}" versjon="{fme:get-attribute("vegObjekt.versjon")}">
              <egenskaper>
              {fme:get-list-attribute("egenskaper{}.egenskap.XML")}
              {if( fme:has-attribute("_geometry")) then
              <egenskap typeId="{fme:get-attribute("_geometriegenskap")}" operasjon="oppdater">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjon.XML")}
              </assosiasjoner>
              else ()}
              <lokasjon operasjon="oppdater">
                  <punkt lenkeId="{fme:get-attribute("ReflinkOID")}" posisjon="{fme:get-attribute("Measure")}" />
              </lokasjon>
          </vegObjekt>
      else
          <vegObjekt typeId="{fme:get-attribute("vegObjekt.typeId")}" tempId="-{fme:get-attribute("tempId")}">
              <egenskaper>
              {fme:get-list-attribute("egenskaper{}.egenskap.XML")}
              {if( fme:has-attribute("_geometry")) then
              <egenskap typeId="{fme:get-attribute("_geometriegenskap")}">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjon.XML")}
              </assosiasjoner>
              else ()}
              <lokasjon>
                  <punkt lenkeId="{fme:get-attribute("ReflinkOID")}" posisjon="{fme:get-attribute("Measure")}" />
              </lokasjon>
          </vegObjekt>}
    -> StringReplacer_3

Bookmark: Oversetter egenskapsnavn fra SOSI-format til modellnavn
Note: Oversetter objekttypenavn til SOSI-formatnavn
SchemaMapper
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ftid,number,3,0,name,char,18,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCECOL = name
    IDXSOURCEATTR = fme_feature_type
    CSV_SCAN_MAX_FEATURES = 1000
    CSV__DUPLICATE_DELIMS = no
    CSV__ALLOW_SPACES_IN_COLUMN_NAMES = yes
    CSV__SCHEMA = number,3,0,char,18,
    DATASET = C:\DATA\GitHub\NVDBGML\XSD\GLA\glabelysning_ftSOSIMapping.csv
    IDXDESTCOL = ftid
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> SchemaMapper_2
Note: Oversetter egenskapsnavn fra SOSI-formatnavn til korrekte modellnavn
SchemaMapper_2
    MATCH_ATTRS = ft_attr ftid
    MAP_ATTRS = ptid name """"""
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ft_attr,char,17,,ftid,number,3,0,ptid,number,6,0,name,char,22,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXSOURCECOL = ""
    IDXSOURCEATTR = fme_feature_type
    CSV_SCAN_MAX_FEATURES = 1000
    CSV__DUPLICATE_DELIMS = no
    CSV__ALLOW_SPACES_IN_COLUMN_NAMES = yes
    CSV__SCHEMA = char,17,,number,3,0,number,6,0,char,22,
    DATASET = C:\DATA\GitHub\NVDBGML\XSD\GLA\glabelysning_ptSOSIMapping.csv
    IDXDESTCOL = ""
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> SchemaMapper_3
Note: Oversetter objekttypenavn tilbake til til korrekte modellnavn
SchemaMapper_3
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ftid,number,3,0,name,char,18,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCECOL = ftid
    IDXSOURCEATTR = fme_feature_type
    CSV_SCAN_MAX_FEATURES = 1000
    CSV__DUPLICATE_DELIMS = no
    CSV__ALLOW_SPACES_IN_COLUMN_NAMES = yes
    CSV__SCHEMA = number,3,0,char,18,
    DATASET = C:\DATA\GitHub\NVDBGML\XSD\GLA\glabelysning_ftSOSIMapping.csv
    IDXDESTCOL = name
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> SchemaMapper_5

Bookmark: Oversetter navn på objekttyper, egenskaper og tillatte verdier fra modellnavn til NVDB-Id-er
Note: Oversetter objekttypenavn til NVDB-VOT-ID
SchemaMapper_5
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ftid,number,3,0,name,char,18,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCECOL = name
    IDXSOURCEATTR = fme_feature_type
    CSV_SCAN_MAX_FEATURES = 1000
    CSV__DUPLICATE_DELIMS = no
    CSV__ALLOW_SPACES_IN_COLUMN_NAMES = yes
    CSV__SCHEMA = number,3,0,char,18,
    DATASET = C:\DATA\GitHub\NVDBGML\XSD\GLA\glabelysning_ftMapping.csv
    IDXDESTCOL = ftid
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> SchemaMapper_6
Note: Oversetter egenskapsnavn til NVDB-ET-ID vha mappingtabell ptMapping
SchemaMapper_6
    MATCH_ATTRS = ft_attr ftid
    MAP_ATTRS = name ptid $(FME_ASC_16)
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ft_attr,char,17,,ftid,number,4,0,ptid,number,6,0,name,char,43,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXSOURCECOL = ""
    IDXSOURCEATTR = fme_feature_type
    CSV_SCAN_MAX_FEATURES = 1000
    CSV__DUPLICATE_DELIMS = no
    CSV__ALLOW_SPACES_IN_COLUMN_NAMES = yes
    CSV__SCHEMA = char,17,,number,4,0,number,6,0,char,43,
    DATASET = C:\DATA\GitHub\NVDBGML\XSD\GLA\glabelysning_ptMapping.csv
    IDXDESTCOL = ""
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> SchemaMapper_4
Note: Oversetter tillatte verdier til NVDB-tillatte verdier
SchemaMapper_4
    MATCH_ATTRS = ptid name
    MAP_ATTRS = name ptid fullname
    CSV__SKIP_LINES = 1
    CSV__GROUP_BY_DATASET = no
    TABLE = CSV
    ROW_ID_ATTR = _schemamapper_row_ids
    CSV__IN_SEPARATOR = ;
    CSV__STRIP_QUOTES = yes
    CSV__SCHEMA_WITH_COL_NAMES = ptid,number,6,0,enid,number,6,0,name,char,29,,fullname,char,34,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    IDXSOURCECOL = ""
    IDXSOURCEATTR = fme_feature_type
    CSV_SCAN_MAX_FEATURES = 1000
    CSV__DUPLICATE_DELIMS = no
    CSV__ALLOW_SPACES_IN_COLUMN_NAMES = yes
    CSV__SCHEMA = number,6,0,number,6,0,char,29,,char,34,
    DATASET = C:\DATA\GitHub\NVDBGML\XSD\GLA\glabelysning_enMapping.csv
    IDXDESTCOL = ""
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    CSV__IN_FIELD_NAMES = YES
    CSV__SKIP_FOOTER = 0
    IDXDESTATTR = fme_feature_type
    MAPPED -> GeometryExtractor
    UNMAPPED -> GeometryExtractor

Bookmark: Finner posisjon i vegnettet - felles posisjon for alle med samme geometri, for å sikre lik posisjon på assosierte objekter
Note: Spesialhåndtering av objekter med lik eller nesten lik geometri, for å sikre lik stedfesting i vegnettet. Lite generisk håndtering...
Note: Strekningshåndtering... / Må finne geometri for start- og sluttpunkt, og deretter LR-posisjon for dem. / Først låse til en lenke, vha strekningsobjektet sitt senterpunkt?
Note: Håndtering av eksisterende (endra) objekter...
GeometryExtractor
    KIND_LONG = FME Binary
    OGC_WKT_PRECISION_DISPLAY = Shortened 64-bit
    ATTR = _geometry
    PRECISION = 0
    OGEOSMS_URL_PREFIX = http://maps.google.com/?q=
    OGCVERSION = 1.1
    REMOVE_GEOMETRY = No
    MSSQL_FORMAT_CHOICE = Geometry
    GEOHASH_PRECISION_DISPLAY = ~9.3 mm (12 characters)
    PREFER_POLYGON_OVER_SURFACE = No
    ELLIPSOID_NAME = WGS84
    LETTERING = WGS84
    OMIT_NAMESPACES_DISPLAY = No
    LEVELS_ATTR = _levels
    -> Snapper
Note: Snapper [Snapper:5] / Group By: <not set> / Tolerance: 1 / Add Additional Vertex: NEVER / Type of Snapping: Vertex Snapping / Save Short Lines: Yes / Version: 5 / Last Parameter Edit: Build 16481
Snapper
    EXTEND_LINES = NEVER
    SAVE_SHORT_LINES = Yes
    SNAPTYPE_PARAM = Vertex Snapping
    TOLERANCE = 1
    SNAPPED -> Matcher_2
    UNTOUCHED -> Matcher_2
Note: Slår sammen til ett søk for alle med lik geometri etter snapping
Matcher_2
    MATCH = 2D
    BLANK_AND_MISSING_DIFFER = No
    CNT_ATTR = _match_id
    LENIENT_MATCH = No
    SM_LIST_NAME = _matchlist
    MATCH_STRATEGY = Match Selected Attributes
    SINGLE_MATCHED -> AttributeKeeper
    NOT_MATCHED -> CenterPointExtractor
AttributeKeeper
    KEEP_LIST = _matchlist{}
    KEEP_ATTRS = _geometry
    -> CenterPointExtractor
CenterPointExtractor
    CENTY = _y
    MODE = Center
    CENTX = _x
    CENTZ = _z
    -> AttributeCreator_2
AttributeCreator_2
    ATTR_TABLE = SET_TO httpReq = https://www.vegvesen.no/nvdb/api/v2/posisjon.xml?nord=@Value(_y)&ost=@Value(_x)&vegreferanse=K
    -> HTTPCaller_2
Note: Finner vegreferanse for representasjonspunktet, med filter på vegkategori=K
HTTPCaller_2
    SAVE_FILE = Attribute
    FOLLOW_REDIRECTS = Yes
    TRANSFER_TIMEOUT_LENGTH = 90
    USE_COOKIES = No
    HTTP_METHOD = GET
    TARGET_ATTR_ENCODING = auto-detect
    RESPONSE_HEADER_LIST_ATTR = _headers
    VERIFY_SSL_CERTIFICATES = Yes
    TARGET_ATTR = _response_body
    ERROR_ATTR = _error
    TARGET_URL = @Value(httpReq)
    CONNECTION_TIMEOUT_LENGTH = 60
    STATUS_CODE_ATTR = _http_status_code
    FILE_TYPE = <Auto Detect from HTTP Headers>
    -> XMLFlattener_2
    <Rejected> -> AttributeCreator_3
XMLFlattener_2
    ATTRIBUTE_XML = _response_body
    XML_SOURCE_TYPE = Attribute with XML document
    EMBEDDED_EXPRESSIONS = veglenke
    NEW_ATTRIBUTES = id posisjon
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    -> TestFilter
Note: Ekstra kontroll på at objektene har fått posisjon. Får en del tilfeller der det ikke gis feil, men bare tomt svar
TestFilter
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_5
    <UNFILTERED> -> AttributeCreator_3
XMLFlattener_5
    ATTRIBUTE_XML = _response_body
    XML_SOURCE_TYPE = Attribute with XML document
    EMBEDDED_EXPRESSIONS = vegreferanse
    NEW_ATTRIBUTES = fylke kommune kategori status nummer hp meter kortform
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    -> AttributeManager_2
AttributeCreator_3
    ATTR_TABLE = SET_TO httpReq = https://www.vegvesen.no/nvdb/api/v2/posisjon.xml?nord=@Value(_y)&ost=@Value(_x)
    -> HTTPCaller_3
Note: Finner vegreferanse for representasjonspunktet, uten filter på vegkategori
HTTPCaller_3
    SAVE_FILE = Attribute
    FOLLOW_REDIRECTS = Yes
    TRANSFER_TIMEOUT_LENGTH = 90
    USE_COOKIES = No
    HTTP_METHOD = GET
    TARGET_ATTR_ENCODING = auto-detect
    RESPONSE_HEADER_LIST_ATTR = _headers
    VERIFY_SSL_CERTIFICATES = Yes
    TARGET_ATTR = _response_body
    ERROR_ATTR = _error
    TARGET_URL = @Value(httpReq)
    CONNECTION_TIMEOUT_LENGTH = 60
    STATUS_CODE_ATTR = _http_status_code
    FILE_TYPE = <Auto Detect from HTTP Headers>
    -> XMLFlattener_4
    <Rejected> -> IngenPosisjon
XMLFlattener_4
    ATTRIBUTE_XML = _response_body
    XML_SOURCE_TYPE = Attribute with XML document
    EMBEDDED_EXPRESSIONS = veglenke
    NEW_ATTRIBUTES = id posisjon
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    -> TestFilter_2
Note: Ekstra kontroll på at objektene har fått posisjon. Får en del tilfeller der det ikke gis feil, men bare tomt svar
TestFilter_2
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_3
    <UNFILTERED> -> IngenPosisjon
XMLFlattener_3
    ATTRIBUTE_XML = _response_body
    XML_SOURCE_TYPE = Attribute with XML document
    EMBEDDED_EXPRESSIONS = vegreferanse
    NEW_ATTRIBUTES = fylke kommune kategori status nummer hp meter kortform
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    -> AnnenVegkategori
    -> AttributeManager_2
AttributeManager_2
    ATTR_TABLE:
      REMOVE httpReq
      REMOVE _x
      REMOVE _y
      REMOVE _z
      REMOVE _error
      REMOVE _headers{}.name
      REMOVE _headers{}.value
      REMOVE _response_body
      REMOVE _http_status_code
      RENAME_SET_VALUE id > ReflinkOID
      RENAME_SET_VALUE posisjon > Measure
      REMOVE fylke
      REMOVE kommune
      RENAME_SET_VALUE kategori > vegident.Vegident.vegkategori
      RENAME_SET_VALUE status > vegident.Vegident.vegstatus
      RENAME_SET_VALUE nummer > vegident.Vegident.vegnummer
      RENAME_SET_VALUE hp > vegparsell.Vegparsell.hovedParsell
      RENAME_SET_VALUE meter > vegparsell.Vegparsell.veglenkeMeterFra
      SET_TO vegparsell.Vegparsell.veglenkeMeterTil = @Value(vegparsell.Vegparsell.veglenkeMeterFra)
      REMOVE kortform
      SET_TO vk = @Value(vegident.Vegident.vegkategori)
    -> ListExploder
Note: Henter fram igjen alle
ListExploder
    INDEX_ATTR = _element_index
    ATTR_CONFLICT_RES = Use Incoming List
    LIST_ATTR = _matchlist{}
    ATTR_ACCUM_MODE = Merge Incoming List
    ELEMENTS -> UUIDGenerator
    <REJECTED> -> UUIDGenerator
UUIDGenerator
    UUID_ATTR = gml_id
    -> GeometryReplacer
Note: Går tilbake til original geometri
GeometryReplacer
    KIND_LONG = FME Binary
    REMOVE_ATTRIBUTE = Yes
    SOURCE = @Value(_geometry)
    -> Counter
AnnenVegkategori: Inspector
    TACKATTRS = kategori
IngenPosisjon: Inspector

Bookmark: Lager geometristreng
AttributeManager
    ATTR_TABLE:
      RENAME_SET_VALUE ENDRINGSFLAGG.ENDRET_TID > endringsflagg.Endringsflagg.tidspunktEndring = FME_CONDITIONAL:DEFAULT_VALUE'@Value(DATAFANGSTDATO)'BOOL_OP;OR;COMPOSITE_TEST;<Unused>;TEST @Value(ENDRINGSFLAGG.ENDRET_TID) ATTRIBUTE_HAS_VALUE _FME_BLANK_STRING_'@Value(ENDRINGSFLAGG.ENDRET_TID)'FME_NUM_CONDITIONS2___
      RENAME_SET_VALUE ENDRINGSFLAGG.ENDRET_TYPE > endringsflagg.Endringsflagg.typeEndring
      RENAME_SET_VALUE DATAFANGSTDATO > datafangstdato
      RENAME_SET_VALUE KVALITET.MÅLEMETODE > kvalitet.Posisjonskvalitet.målemetode
      RENAME_SET_VALUE KVALITET.SYNBARHET > kvalitet.Posisjonskvalitet.synbarhet
      RENAME_SET_VALUE HREF > høydereferanse
      RENAME_SET_VALUE KVALITET.NØYAKTIGHET > kvalitet.Posisjonskvalitet.nøyaktighet
      SET_TO identifikasjon.Identifikasjon.navnerom = TromsøKommune
      SET_TO identifikasjon.Identifikasjon.lokalId = @Value(tempId)
      SET_TO identifikasjon.Identifikasjon.versjonId = 1
    -> AttributeExposer
AttributeExposer
    ATTR_LIST = fme_basename,fme_feature_type
    -> CoordinateRounder
CoordinateRounder
    YPREC = 3
    ZPREC = 3
    XPREC = 3
    ROUNDED -> CoordinateConcatenator
CoordinateConcatenator
    COORD_DELIM = ,
    PRECISION = No
    COORDINATES_TO_INCLUDE_DIS = X Y Z
    ELEMENT_DELIM = " "
    COORD_ATTR = _coordinates
    -> StringConcatenator
Note: Hardkoding av punktgeometristreng
StringConcatenator
    PARM_LINE = POINT(@Value(_coordinates))
    ACTION = Create New Attribute
    VAL_ATTR = _geometry
    -> PythonCaller
Note: Kvalitetsstreng
PythonCaller
    PYTHONSOURCE:
      import fmeobjects
      # Template Function interface:

      def setQuality(feature):
          qs=""
          qm = feature.getAttribute('kvalitet.Posisjonskvalitet.målemetode')
          qms=str(qm)
          if qms <> "None":
              qs="målemetode="+qms

          qm = feature.getAttribute('kvalitet.Posisjonskvalitet.nøyaktighet')
          qms=str(qm)
          if qms <> "None":
              qs=qs+"; nøyaktighet="+qms

          qm = feature.getAttribute('kvalitet.Posisjonskvalitet.synbarhet')
          qms=str(qm)
          if qms <> "None":
              qs=qs+"; synbarhet="+qms

          qm = feature.getAttribute('kvalitet.Posisjonskvalitet.målemetodeHøyde')
          qms=str(qm)
          if qms <> "None":
              qs=qs+"; målemetodeHøyde="+qms

          qm = feature.getAttribute('kvalitet.Posisjonskvalitet.nøyaktighetHøyde')
          qms=str(qm)
          if qms <> "None":
              qs=qs+"; nøyaktighetHøyde="+qms

          if qs <> "":
              feature.setAttribute('qualityString', qs+'; ')
    PYTHONSYMBOL = setQuality
    NEW_ATTRIBUTES = qualityString
    -> AttributeValueMapper
Note: Hardkoding av Id for geometriegenskap
AttributeValueMapper
    SRC = fme_feature_type
    DIRECTION = Forward (Source To Destination)
    VAL_ATTR = _geometriegenskap
    LUT = 87,4787,181,4838,88,4788
    -> TestFilter_3
    -> TestFilter_5

Bookmark: Hardkoda, ikke permanent løsning for å finne assosierte objekter
TestFilter_5
    TEST_LIST = BOOL_OP,OR,COMPOSITE_TEST,<Unused>,TEST_CLAUSE,"TEST @Value(fme_feature_type) = 181",Lysmast,BOOL_OP,OR,COMPOSITE_TEST,<Unused>,TEST_CLAUSE,"TEST @Value(fme_feature_type) = 88",Lysarmatur,BOOL_OP,OR,COMPOSITE_TEST,<Unused>,TEST_CLAUSE,"TEST @Value(fme_feature_type) = 87",Belysningspunkt
    DEFAULT_VALUE = <UNFILTERED>
    Lysmast -> NullAttributeMapper
    Lysarmatur -> NullAttributeMapper
    Belysningspunkt -> NeighborFinder [BASE]
Note: Finner assosiasjoner innenfor 1m
NeighborFinder
    TREAT_POLYGON_AS = Lines
    CANDIDATES_FIRST = No
    CLOSE_LIST_NAME = assosiasjoner
    INSERT_VERTEX = No
    INCOMING_PREFIX = assosiasjoner.
    K = 2
    ATTR_ACCUM_MODE = Prefix Candidate
    MODE = Bases and Candidates
    MAX = 1
    MATCHED -> ListElementCounter
    UNMATCHED_BASE -> ListElementCounter
ListElementCounter
    CNT_ATTR = assosiasjoner.antall
    LIST_NAME = assosiasjoner{}
    -> NullAttributeMapper

Bookmark: Spesialhåndtering av assosiert Lysarmatur og Lysmast, ikke permanent løsning
TestFilter_3
    TEST_LIST = BOOL_OP,OR,COMPOSITE_TEST,<Unused>,TEST_CLAUSE,"TEST @Value(fme_feature_type) = 181",Lysmast,BOOL_OP,OR,COMPOSITE_TEST,<Unused>,TEST_CLAUSE,"TEST @Value(fme_feature_type) = 88",Lysarmatur
    DEFAULT_VALUE = <UNFILTERED>
    Lysmast -> AttributeManager_10
    Lysarmatur -> AttributeManager_10
AttributeManager_10
    ATTR_TABLE:
      REMOVE endringsflagg.Endringsflagg.tidspunktEndring
      SET_TO assosiasjon.typeId = FME_CONDITIONAL:DEFAULT_VALUE'_FME_NO_OP_'BOOL_OP;OR;COMPOSITE_TEST;<Unused>;TEST @Value(fme_feature_type) = 181'220027'BOOL_OP;OR;COMPOSITE_TEST;<Unused>;TEST @Value(fme_feature_type) = 88'220028'FME_NUM_CONDITIONS3___
      SET_TO assosiasjon.operasjon = FME_CONDITIONAL:DEFAULT_VALUE'_FME_NO_OP_'BOOL_OP;OR;COMPOSITE_TEST;<Unused>;TEST @Value(endringsflagg.Endringsflagg.typeEndring) = E'oppdater'FME_NUM_CONDITIONS2___
      SET_TO endringsflagg.Endringsflagg.typeEndring = N
    -> AttributeKeeper_6
AttributeKeeper_6
    KEEP_ATTRS = tempId,endringsflagg.Endringsflagg.typeEndring,ReflinkOID,assosiasjon.typeId,Measure,fme_basename,assosiasjon.operasjon,gml_id,fme_feature_type
    -> assosiasjonXML [ROOT]
assosiasjonXML: XMLTemplater
    RESULT_ATTRIBUTE = assosiasjon.XML
    VISIBLE_QUERY_VALIDATE = Yes
    OUTPUT_XML_HEADER = No
    ROOT_QUERY_EXPR:
      {if( fme:has-attribute("assosiasjon.operasjon")) then
      <assosiasjon typeId="{fme:get-attribute("assosiasjon.typeId")}" operasjon="{fme:get-attribute("assosiasjon.operasjon")}"><tempId>-{fme:get-attribute("tempId")}</tempId></assosiasjon>
      else
      <assosiasjon typeId="{fme:get-attribute("assosiasjon.typeId")}"><tempId>-{fme:get-attribute("tempId")}</tempId></assosiasjon>}
    -> AttributeKeeper_4
AttributeKeeper_4
    KEEP_ATTRS = assosiasjon.XML,tempId,assosiasjon.typeId,fme_basename,assosiasjon.operasjon,gml_id,fme_feature_type
    -> NeighborFinder [CANDIDATE]

Bookmark: Liste med egenskaper
AttributeExploder
    ATTR_VALUE_LABEL = _attr_value
    KEEP_ATTRIBUTES = Yes
    ATTR_NAME_LABEL = _attr_name
    EXPLODING_TYPE = Features
    KEEP_GEOMETRY = No
    -> AttributeKeeper_5
AttributeKeeper_5
    KEEP_ATTRS = endringsflagg.Endringsflagg.typeEndring,_attr_value,tempId,_attr_name
    -> AttributeValidator
AttributeValidator
    TABLE = _attr_name|TYPE|NUM
    PASSED -> AttributeManager_9
AttributeManager_9
    ATTR_TABLE:
      RENAME_SET_VALUE _attr_name > egenskap.typeId
      RENAME_SET_VALUE _attr_value > egenskap.verdi
      SET_TO egenskap.operasjon = FME_CONDITIONAL:DEFAULT_VALUE'_FME_NO_OP_'BOOL_OP;OR;COMPOSITE_TEST;<Unused>;TEST @Value(endringsflagg.Endringsflagg.typeEndring) = E'oppdater'FME_NUM_CONDITIONS2___
    -> egenskapXML [ROOT]
egenskapXML: XMLTemplater
    RESULT_ATTRIBUTE = egenskap.XML
    VISIBLE_QUERY_VALIDATE = Yes
    OUTPUT_XML_HEADER = No
    ROOT_QUERY_EXPR:
      {if( fme:has-attribute("egenskap.operasjon")) then
      <egenskap typeId="{fme:get-attribute("egenskap.typeId")}" operasjon="{fme:get-attribute("egenskap.operasjon")}">
          <verdi>{fme:get-attribute("egenskap.verdi")}</verdi>
      </egenskap>
      else
      <egenskap typeId="{fme:get-attribute("egenskap.typeId")}">
          <verdi>{fme:get-attribute("egenskap.verdi")}</verdi>
      </egenskap>}
    -> ListBuilder_2
ListBuilder_2
    LIST_NAME = egenskaper
    GRP_BY = tempId
    -> FeatureMerger_5 [SUPPLIER]

Bookmark: Opprydding i tekst
StringReplacer_3
    FIND_TEXT = &lt;
    NO_MATCH = _FME_NO_OP_
    REPLACE_TEXT = <
    REGEXP = NO
    SRC_ATTRS = vegObjekt.XML
    CASE = NO
    -> StringReplacer_4
StringReplacer_4
    FIND_TEXT = &gt;
    NO_MATCH = _FME_NO_OP_
    REPLACE_TEXT = >
    REGEXP = NO
    SRC_ATTRS = vegObjekt.XML
    CASE = NO
    -> AttributeRemover_4
AttributeRemover_4
    LIST_ATTRS = egenskaper{}
    -> ListBuilder_3
ListBuilder_3
    LIST_NAME = vegObjektliste
    GRP_BY = endringsflagg.Endringsflagg.typeEndring
    -> EndringssettXML [ROOT]
EndringssettXML: XMLTemplater
    RESULT_ATTRIBUTE = endringssett.XML
    VISIBLE_QUERY_VALIDATE = Yes
    OUTPUT_XML_HEADER = No
    ROOT_QUERY_EXPR:
        {if( {fme:get-attribute("endringsflagg.Endringsflagg.typeEndring")}="E") then
        <delvisOppdater>
          <vegObjekter>
          {fme:get-list-attribute("vegObjektliste{}.vegObjekt.XML")}
          </vegObjekter>
        </delvisOppdater>
        else if( {fme:get-attribute("endringsflagg.Endringsflagg.typeEndring")}="N") then
        <registrer>
          <vegObjekter>
          {fme:get-list-attribute("vegObjektliste{}.vegObjekt.XML")}
          </vegObjekter>
        </registrer>
        else ()}
    -> AttributeKeeper_7

Bookmark: Opprydding
AttributeKeeper_7
    KEEP_ATTRS = endringsflagg.Endringsflagg.typeEndring,fme_basename,endringssett.XML
    -> StringReplacer_5
StringReplacer_5
    FIND_TEXT = &lt;
    NO_MATCH = _FME_NO_OP_
    REPLACE_TEXT = <
    REGEXP = NO
    SRC_ATTRS = endringssett.XML
    CASE = NO
    -> StringReplacer_6
StringReplacer_6
    FIND_TEXT = &gt;
    NO_MATCH = _FME_NO_OP_
    REPLACE_TEXT = >
    REGEXP = NO
    SRC_ATTRS = endringssett.XML
    CASE = NO
    -> ListBuilder_4
ListBuilder_4
    LIST_NAME = endringsliste
    -> TimeStamper
TimeStamper
    FMT = ^Y-^m-^d
    TIME_ATTR = _timestamp
    -> EndringslisteXML [ROOT]
EndringslisteXML: XMLTemplater
    RESULT_ATTRIBUTE = endringsliste.XML
    VISIBLE_QUERY_VALIDATE = Yes
    OUTPUT_XML_HEADER = No
    ROOT_QUERY_EXPR:
      <endringssett xmlns="http://nvdb.vegvesen.no/apiskriv/domain/v2" effektDato="{fme:get-attribute("_timestamp")}" datakatalogversjon="$(DakatVersjon)">
      {fme:get-list-attribute("endringsliste{}.endringssett.XML")}
      </endringssett>
    -> StringReplacer

Bookmark: Opprydding
StringReplacer
    FIND_TEXT = &lt;
    NO_MATCH = _FME_NO_OP_
    REPLACE_TEXT = <
    REGEXP = NO
    SRC_ATTRS = endringsliste.XML
    CASE = NO
    -> StringReplacer_2
StringReplacer_2
    FIND_TEXT = &gt;
    NO_MATCH = _FME_NO_OP_
    REPLACE_TEXT = >
    REGEXP = NO
    SRC_ATTRS = endringsliste.XML
    CASE = NO
    -> XMLFormatter_2
XMLFormatter_2
    TEXT_INDENT = no
    XML_OUTPUT_TYPE = Attribute
    REMOVE_ALL_COMMENT = No
    WHITESPACE_HANDLING = Preserve all whitespace
    REPLACE_TABS_WITH_SPACES = no
    SCHEMALOC_CLEANUP = No
    XML_INPUT_TYPE = Attribute Specifying XML Text
    COLLAPSE_EMPTY_ELEMENT = No
    XML_OUTPUT_ATTR = _xml_output
    REMOVE_EMPTY_ELEMENT = Yes
    FORMATTING_CHOICE = Pretty-Print XML
    LIST_NAME = _xml_error
    INDENT_SIZE = 1
    XML_ATTR_TEXT = endringsliste.XML
    OUTPUT_ENCODING = utf-8
    NAMESPACE_CLEANUP = No
    PASSED -> AttributeRenamer_4
AttributeRenamer_4
    ATTR_TABLE = RENAME_SET_DEFAULT _xml_output > text_line_data
    -> text_line (writer TEXTLINE_1)
Note: En xml-fil pr GML-fil
text_line (writer TEXTLINE_1)
    attributes: text_line_data buffer
