FME workspace gml_gml2none.fmw

Parameters:
- SourceDataset_GML = C:\DATA\GLA\Data\501\GMLData_fra _lillehammer.gml   # Source Geography Markup Language (GML) File(s)
- SourceDataset_GML_3 = C:\DATA\GLA\Data\402\GMLData.gml   # Source Geography Markup Language (GML) File(s)
- DestDataset_GML = C:\DATA\GLA\Data\Transformert   # Destination Geography Markup Language (GML) File

Readers:
- GML_1: GML from $(SourceDataset_GML)
- GML_2: GML from $(SourceDataset_GML_3)

Writers:
- GML_3: GML to $(DestDataset_GML)

Note: belysningsstrekning: GMLData_fra _lillehammer [GML]
belysningsstrekning (reader GML_1)
    attributes: byggeaar xml_decimal(5,0), datafangstdato xml_char(20), kommunenummer xml_decimal(5,0), navnpaastrekning xml_char(15), objid xml_decimal(2,0), objtype xml_char(6)
    -> AttributeExposer
Note: belysningsstrekning: GMLData [GML]
belysningsstrekning (reader GML_2)
    attributes: byggeaar xml_decimal(5,0), objid xml_decimal(3,0)
    -> AttributeExposer
AttributeExposer
    ATTR_LIST = fme_basename,fme_feature_type
    -> AttributeManager
AttributeManager
    ATTR_TABLE:
      RENAME_SET_VALUE byggeaar > byggeår
      RENAME_SET_VALUE navnpaastrekning > navnPåStrekning
      SET_TO fme_feature_type = Belysningspunkt
    -> Belysningsstrekning (writer GML_3)
    -> belysningsstrekning
belysningsstrekning: Inspector [off]
Belysningsstrekning (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, bruksområde xml_buffer, type xml_buffer, navnPåStrekning xml_buffer, byggeår xml_int64, tenningssystem xml_buffer, dimming xml_buffer, fjernstyring xml_buffer, avstandInnbyrdes xml_int64, kommentar{}.Kommentar.beskrivelse xml_buffer,
      kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer, kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, luminansnivå xml_buffer, eier xml_buffer, eierNavn xml_buffer, vedlikeholdsansvarlig xml_buffer, senterlinje xml_geometry, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer, assosiertBelysningspunkt{}.owns xml_boolean, assosiertBelysningspunkt{}.nilReason xml_buffer, assosiertBelysningspunkt{}.gml_remoteSchema xml_buffer, assosiertBelysningspunkt{}.xlink_href xml_buffer
tennpunkt (reader GML_2)
    attributes: driftsattaar xml_decimal(5,0), objid xml_decimal(2,0)
    -> AttributeExposer_4
AttributeExposer_4
    ATTR_LIST = fme_basename,fme_feature_type
    -> AttributeManager_4
AttributeManager_4
    ATTR_TABLE:
      SET_TO fme_feature_type = Tennpunkt
      RENAME_SET_VALUE driftsattaar > driftsattår
    -> tennpunkt
    -> Tennpunkt (writer GML_3)
Tennpunkt (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, tennpunktnummer xml_buffer, spenning xml_buffer, produktnavn xml_buffer, produsentnavn xml_buffer, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer,
      kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, driftsmerking xml_buffer, driftsattår xml_int64, posisjon xml_geometry, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer
tennpunkt: Inspector [off]
lysarmatur (reader GML_2)
    attributes: antallarmatureribelysningspkt xml_decimal(2,0), objid xml_decimal(3,0), optikk xml_char(10), produsentnavnarmatur xml_char(8)
    -> AttributeExposer_5
AttributeExposer_5
    ATTR_LIST = fme_basename,fme_feature_type
    -> AttributeManager_5
AttributeManager_5
    ATTR_TABLE:
      SET_TO fme_feature_type = Lysarmatur
      RENAME_SET_VALUE antallarmatureribelysningspkt > antallArmaturerIBelysningspkt
      RENAME_SET_VALUE produsentnavnarmatur > produsentnavnArmatur
    -> Lysarmatur (writer GML_3)
    -> lysarmatur
lysarmatur: Inspector [off]
Lysarmatur (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, lyskildeType xml_buffer, effekt xml_real64, driftsmerking xml_buffer, driftsattår xml_int64, høydeOverVeg xml_real64, antallLyskilderPerArmatur xml_buffer, antallArmaturerIBelysningspkt xml_buffer, inngårINødsystemet xml_buffer, produktnavnArmatur xml_buffer,
      produsentnavnArmatur xml_buffer, lysflux xml_int64, produsentnavnDriver xml_buffer, produsentnavnLyskilde xml_buffer, lEDEffektArmaturTotaltTest xml_int64, fargetemperatur xml_int64, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer, kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, optikk xml_buffer, konstantLysutbytte xml_buffer, dimming xml_buffer, utystyrsklasse xml_buffer, driftsstrømUdimmet xml_int64, lEDAntallDioder xml_int64, lEDEffektPerStkTest xml_real64, avskjermingType xml_buffer, avskjermingMateriale xml_buffer, fargegjengivelsesindeks xml_int64, utskiftbareLyskilder xml_buffer, armaturnummer xml_buffer, kommunikasjonsenhet xml_buffer, eier xml_buffer, eierNavn xml_buffer,
      vedlikeholdsansvarlig xml_buffer, posisjon xml_geometry, felt xml_buffer, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer
Note: lysmast: GMLData [GML]
lysmast (reader GML_2)
    attributes: byggeaar xml_decimal(5,0), eiernavn xml_decimal(5,0), fundamentering xml_char(15), kommunenummer xml_decimal(5,0), objid xml_decimal(3,0), overflatebehandling xml_char(12), produsentnavn xml_char(9), totalmastelengde xml_decimal(2,0), type xml_char(15), vedlikeholdsansvarlig xml_decimal(5,0)
    -> AttributeExposer_2
Note: lysmast: GMLData_fra _lillehammer [GML]
lysmast (reader GML_1)
    attributes: byggeaar xml_decimal(5,0), kommunenummer xml_decimal(5,0), lokalid xml_char(8), objid xml_decimal(2,0), objtype xml_char(5)
    -> AttributeExposer_2
AttributeExposer_2
    ATTR_LIST = fme_basename,fme_feature_type
    -> AttributeManager_2
AttributeManager_2
    ATTR_TABLE:
      RENAME_SET_VALUE byggeaar > byggeår
      SET_TO fme_feature_type = Lysmast
      RENAME_SET_VALUE eiernavn > eierNavn
      RENAME_SET_VALUE totalmastelengde > totalMastelengde
    -> Lysmast (writer GML_3)
    -> lysmast
Lysmast (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, type xml_buffer, produktnavn xml_buffer, ettergivendeMast xml_buffer, byggeår xml_int64, driftsmerking xml_buffer, fundamentering xml_buffer, boltavstandFotplate xml_buffer, diameter xml_int64, diameterTopp xml_int64,
      totalMastelengde xml_real64, utligger xml_buffer, vedlikeholdsansvarlig xml_buffer, utliggerarmensLengde xml_real64, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer, kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, bardunStrever xml_buffer, overflatebehandling xml_buffer, rALKode xml_buffer, produsentnavn xml_buffer, eier xml_buffer, eierNavn xml_buffer, posisjon xml_geometry, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer
lysmast: Inspector [off]
elektriskanlegg (reader GML_2)
    attributes: driftsattaar xml_decimal(5,0), objid xml_decimal(2,0), plasseringmaaler xml_char(21)
    -> AttributeExposer_6
AttributeExposer_6
    ATTR_LIST = fme_basename,fme_feature_type
    -> AttributeManager_6
AttributeManager_6
    ATTR_TABLE:
      SET_TO fme_feature_type = ElektriskAnlegg
      RENAME_SET_VALUE driftsattaar > driftsattår
      RENAME_SET_VALUE plasseringmaaler > plasseringMåler
    -> elektriskanlegg
    -> ElektriskAnlegg (writer GML_3)
ElektriskAnlegg (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, anleggsnummer xml_buffer, bruksområde xml_buffer, målepunktID xml_buffer, eier xml_buffer, byggetEtterNorm xml_buffer, driftsmerking xml_buffer, spenning xml_buffer, kundenummer xml_buffer, målernummer xml_buffer,
      fjernavlesing xml_buffer, inngårINødsystemet xml_buffer, jordelektrode xml_buffer, jordfeilbryter xml_buffer, jordfeilvarsling xml_buffer, målingType xml_buffer, nettselskap xml_buffer, nettsystem xml_buffer, tilleggsinformasjon xml_buffer, plasseringMåler xml_buffer, byggetEtterForskrift xml_buffer, merknad xml_buffer, effekt xml_int64, integrertMed xml_buffer, vedlikeholdsansvarlig xml_buffer, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer, kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, driftsattår xml_int64, eierNavn xml_buffer, posisjon xml_geometry, dokumentasjon{}.Dokumentasjon.dato xml_date, dokumentasjon{}.Dokumentasjon.type xml_buffer, dokumentasjon{}.Dokumentasjon.filnavn xml_buffer,
      dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer, assosiertBelysningsstrekning{}.owns xml_boolean, assosiertBelysningsstrekning{}.nilReason xml_buffer, assosiertBelysningsstrekning{}.gml_remoteSchema xml_buffer, assosiertBelysningsstrekning{}.xlink_href xml_buffer, assosiertBelysningspunkt{}.owns xml_boolean, assosiertBelysningspunkt{}.nilReason xml_buffer, assosiertBelysningspunkt{}.gml_remoteSchema xml_buffer, assosiertBelysningspunkt{}.xlink_href xml_buffer
elektriskanlegg: Inspector [off]
Note: belysningspunkt: GMLData_fra _lillehammer [GML]
belysningspunkt (reader GML_1)
    attributes: antall xml_decimal(2,0), eier xml_char(20), eiernavn xml_char(20), kommunenummer xml_decimal(5,0), lokalid xml_char(8), noeyaktighet xml_decimal(3,0), noeyaktighethoeyde xml_decimal(4,0), objid xml_decimal(3,0), objtype xml_char(19)
    -> AttributeExposer_3
Note: belysningspunkt: GMLData [GML]
belysningspunkt (reader GML_2)
    attributes: datafangstdato xml_char(20), objid xml_decimal(3,0), oppdateringsdato xml_char(20), stroemtilfoerselkategori xml_char(10)
    -> AttributeExposer_3
AttributeExposer_3
    ATTR_LIST = fme_basename,fme_feature_type
    -> AttributeManager_3
AttributeManager_3
    ATTR_TABLE:
      SET_TO fme_feature_type = Belysningspunkt
      RENAME_SET_VALUE eiernavn > eierNavn
      RENAME_SET_VALUE noeyaktighet > kvalitet.Posisjonskvalitet.nøyaktighet
      RENAME_SET_VALUE noeyaktighethoeyde > kvalitet.Posisjonskvalitet.nøyaktighetHøyde
      RENAME_SET_VALUE stroemtilfoerselkategori > strømtilførselKategori
    -> Belysningspunkt (writer GML_3)
    -> belysningspunkt
Belysningspunkt (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, bruksområde xml_buffer, antall xml_int64, plassering xml_buffer, avstandFraVegkant xml_real64, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer,
      kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, tilstandSkadeBelysning{}.TilstandSkadeBelysning.tilstand xml_buffer, tilstandSkadeBelysning{}.TilstandSkadeBelysning.skadetype xml_buffer, tilstandSkadeBelysning{}.TilstandSkadeBelysning.datoKontrollert xml_date, tilstandSkadeBelysning{}.TilstandSkadeBelysning.tiltak xml_buffer, tilstandSkadeBelysning{}.TilstandSkadeBelysning.tiltakNår xml_buffer, tilstandSkadeBelysning{}.TilstandSkadeBelysning.tilleggsinformasjon xml_buffer, tilstandSkadeBelysning{}.TilstandSkadeBelysning.dokumentasjon{}.Dokumentasjon.dato xml_date, tilstandSkadeBelysning{}.TilstandSkadeBelysning.dokumentasjon{}.Dokumentasjon.type xml_buffer, tilstandSkadeBelysning{}.TilstandSkadeBelysning.dokumentasjon{}.Dokumentasjon.filnavn xml_buffer, tilstandSkadeBelysning{}.TilstandSkadeBelysning.dokumentasjon{}.Dokumentasjon.hyperlink xml_buffer, tilstandSkadeBelysning{}.TilstandSkadeBelysning.dokumentasjon{}.Dokumentasjon.tekst xml_buffer, tilstandSkadeBelysning{}.TilstandSkadeBelysning.dokumentasjon{}.Dokumentasjon.ansvarlig xml_buffer, tilstandSkadeBelysning{}.TilstandSkadeBelysning.dokumentasjon{}.Dokumentasjon.arkiveringskode xml_buffer, tilstandSkadeBelysning{}.TilstandSkadeBelysning.dokumentasjon{}.Dokumentasjon.merknad xml_buffer, tilstandSkadeFUPunkt{}.TilstandSkadeFUPunkt.etterslep xml_buffer, tilstandSkadeFUPunkt{}.TilstandSkadeFUPunkt.datoKontrollert xml_date, tilstandSkadeFUPunkt{}.TilstandSkadeFUPunkt.tilleggsinformasjon xml_buffer, tilstandSkadeFUPunkt{}.TilstandSkadeFUPunkt.dokumentasjon{}.Dokumentasjon.dato xml_date, tilstandSkadeFUPunkt{}.TilstandSkadeFUPunkt.dokumentasjon{}.Dokumentasjon.type xml_buffer, tilstandSkadeFUPunkt{}.TilstandSkadeFUPunkt.dokumentasjon{}.Dokumentasjon.filnavn xml_buffer, tilstandSkadeFUPunkt{}.TilstandSkadeFUPunkt.dokumentasjon{}.Dokumentasjon.hyperlink xml_buffer, tilstandSkadeFUPunkt{}.TilstandSkadeFUPunkt.dokumentasjon{}.Dokumentasjon.tekst xml_buffer, tilstandSkadeFUPunkt{}.TilstandSkadeFUPunkt.dokumentasjon{}.Dokumentasjon.ansvarlig xml_buffer, tilstandSkadeFUPunkt{}.TilstandSkadeFUPunkt.dokumentasjon{}.Dokumentasjon.arkiveringskode xml_buffer, tilstandSkadeFUPunkt{}.TilstandSkadeFUPunkt.dokumentasjon{}.Dokumentasjon.merknad xml_buffer, strømtilførselKategori xml_buffer,
      strømtilførselTypeKabel xml_buffer, overbelastningsvern xml_buffer, fellesføringMedAnnenEtat xml_buffer, fellesføringLeietaker xml_buffer, tilleggsinformasjon xml_buffer, eier xml_buffer, eierNavn xml_buffer, vedlikeholdsansvarlig xml_buffer, posisjon xml_geometry, felt xml_buffer, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer, assosiertLysarmatur{}.owns xml_boolean, assosiertLysarmatur{}.nilReason xml_buffer, assosiertLysarmatur{}.gml_remoteSchema xml_buffer, assosiertLysarmatur{}.xlink_href xml_buffer, assosiertLysmast{}.owns xml_boolean, assosiertLysmast{}.nilReason xml_buffer, assosiertLysmast{}.gml_remoteSchema xml_buffer, assosiertLysmast{}.xlink_href xml_buffer, assosiertTennpunkt{}.owns xml_boolean, assosiertTennpunkt{}.nilReason xml_buffer, assosiertTennpunkt{}.gml_remoteSchema xml_buffer, assosiertTennpunkt{}.xlink_href xml_buffer
belysningspunkt: Inspector [off]
