FME workspace NVDBAPI2GML_V2_2017.fmw

Parameters:
- ftID = 532   # NVDB Vegobjekttype-ID
- omr = kommune   # Områdetype
- omrNvn = 521   # Område
- gmlFolder = C:\DATA\tmp   # GML-hovedmappe
- dwnlAssObj = Nei   # Laste ned assosierte objekter
- gmlNs = https://raw.githubusercontent.com/jetgeo/NVDBGML/master/XSD/NVDB   # GML Namespace
- fullGmlNs:   # Python Script
      ns = FME_MacroValues['gmlNs'] + '/' + FME_MacroValues['ftID']
      return ns
- xsd:   # Python Script
      xsd = FME_MacroValues['fullGmlNs'] + '/' + FME_MacroValues['ftID'] + '.xsd'
      return xsd
- sl:   # Python Script
      sl = FME_MacroValues['fullGmlNs'] + ' ' + FME_MacroValues['fullGmlNs'] + '/' + FME_MacroValues['ftID'] + '.xsd'
      return sl
- namespace = vegvesen.no.nvdb   # Attribute Value
- fullGmlFolder:   # Python Script
      fldr = FME_MacroValues['gmlFolder'] + '\\' + FME_MacroValues['omr'] + '\\' + FME_MacroValues['omrNvn'] + '\\' + FME_MacroValues['ftID']
      return fldr

Writers:
- GML_1: GML to $(fullGmlFolder)

Creator
    NUM = 1
    GEOMTYPE = Geometry Object
    CREATED -> AttributeCreator
AttributeCreator
    ATTR_TABLE = SET_TO href = https://www.vegvesen.no/nvdb/api/v2/vegobjekter/$(ftID)?$(omr)=$(omrNvn)&antall=5000&inkluder=alle
    -> NVDB_Leser [_Input]
FeatureMerger_3
    ATTR_CONFLICT_RES = Use Requestor
    JOIN_KEYS = @Value(identifikasjon.Identifikasjon.lokalId) @Value(identifikasjon.Identifikasjon.lokalId) AUTO
    ATTR_ACCUM_MODE = Merge Supplier
    IGNORE_NULLS = No
    SUPPLIERS_FIRST = No
    GEOM_TYPE = Build Polygons
    REJECT_NULL_MISSING_KEYS = No
    CONNECT_Z_MODE = First Wins
    PROCESS_DUPS = Yes
    MERGE_TYPE = Attributes Only
    MERGED -> FeatureMerger_3_NOT_MERGED_-__SchemaMapper
    NOT_MERGED -> FeatureMerger_3_NOT_MERGED_-__SchemaMapper
FeatureMerger_3_NOT_MERGED_-__SchemaMapper: Junction
    -> SchemaMapper
Note: Ta med assosierte objekter?
Note: Gjenstående problemstilling: Dersom assosiasjon til objekt med multigeometri blir det nå kun lagd assosiasjon til den første delen
TestFilter
    TEST_LIST = BOOL_OP,OR,COMPOSITE_TEST,<Unused>,TEST_CLAUSE,"TEST $(dwnlAssObj) = Ja",AssosiertJa
    DEFAULT_VALUE = <UNFILTERED>
    AssosiertJa -> DuplicateFilter
GeometryPropertySetter_SET: Junction
    -> Vegobjekttype (writer GML_1)
    -> Inspector
Inspector [off]
Vegobjekttype (writer GML_1)
    attributes: id xml_char(200), geometri.wkt xml_char(200), xml_fragment xml_char(200), xml_id xml_char(200), xml_matched_element xml_char(200), xml_parent_id xml_char(200), xml_parent_child_pos xml_char(200), identifikasjon.Identifikasjon.lokalId xml_char(200), identifikasjon.Identifikasjon.versjonId xml_char(200), identifikasjon.Identifikasjon.navnerom xml_char(200), assosiasjoner{}.typeId xml_char(200), assosiasjoner{}.vegobjektId xml_char(200), assosiasjoner{}.relasjonstype xml_char(200), epsg xml_char(200), _hierarchy_child_id_list{} xml_char(200), _geometry_name xml_char(200), _hierarchy_id xml_char(200), _hierarchy_parent_id xml_char(200), _part_number xml_char(200), name xml_char(200), _schemamapper_row_ids xml_char(200), posisjon xml_char(200), senterlinje xml_char(200)

Bookmark: Leser og tolker XML fra NVDB-API
Note: Lesing av XML: / Hente ut neste.ref og metadata.returnert / Løkke med lesing av "href" / Inntill returnert=0
NVDB_Leser
    NESTE.HREF = @Value(href)
    -> FeatureMerger_3 [REQUESTOR]
    -> ListExploder

Bookmark: Lager assosiasjonslister med xlink_href
ListExploder
    ATTR_ACCUM_MODE = Merge Incoming List
    INDEX_ATTR = _element_index
    LIST_ATTR = assosiasjoner{}
    ATTR_CONFLICT_RES = Use Incoming List
    ELEMENTS -> AttributeKeeper_2
    ELEMENTS -> TestFilter
AttributeKeeper_2
    KEEP_ATTRS = vegobjektId,typeId,identifikasjon.Identifikasjon.navnerom,identifikasjon.Identifikasjon.lokalId,identifikasjon.Identifikasjon.versjonId
    -> Joiner
Joiner
    CSV__IN_SEPARATOR = ;
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    ATTR_ACCUM_MODE = Merge Joined
    CSV__GROUP_BY_DATASET = no
    DATASET = https://raw.githubusercontent.com/jetgeo/NVDBGML/master/XSD/NVDB_ftMapping.csv
    CSV__ALLOW_SPACES_IN_COLUMN_NAMES = yes
    ATTR_CONFLICT_RES = Use Original
    CSV__STRIP_QUOTES = yes
    CSV__IN_FIELD_NAMES = YES
    JOIN_KEYS = typeId ftid
    ADDED_FIELDS = name
    CSV__FIELD_NAMES_AFTER_HEADER = no
    CSV__DUPLICATE_DELIMS = no
    CSV__SCHEMA_WITH_COL_NAMES = ftid,number,4,0,name,char,23,
    CSV_SCAN_MAX_FEATURES = 1000
    FORMAT = CSV
    CSV__SKIP_FOOTER = 0
    MATCH_MULTIPLE_DISPLAY = Create a feature for each match
    TABLE = CSV
    CSV__SCHEMA = number,4,0,char,23,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    MATCH_RULE_DISPLAY = Match All (1:M)
    JOINED -> StringConcatenator
StringConcatenator
    VAL_ATTR = xlink_href
    ACTION = Create New Attribute
    PARM_LINE = @Value(name).gml#$(namespace).@Value(vegobjektId)_0
    -> ListBuilder
ListBuilder
    LIST_NAME = _list
    GRP_BY = name identifikasjon.Identifikasjon.navnerom identifikasjon.Identifikasjon.lokalId identifikasjon.Identifikasjon.versjonId
    -> PythonCaller
PythonCaller
    PYTHONSYMBOL = processFeature
    PYTHONSOURCE:
      import fme
      import fmeobjects

      def processFeature(feature):
          anames= feature.getAllAttributeNames()
          lname = "blank"
          #find name attribute value
          for aname in anames:
              if aname == "name":
                  lname = feature.getAttribute(aname)
          #find list attributes and rename/copy to new name
          if lname != "blank":
              for aname in anames:
                  if aname.startswith("_list{"):
                      newAname=aname.replace("_list{","assosiert"+lname+"{")
                      aval = feature.getAttribute(aname)
                      feature.setAttribute(newAname, aval)
    -> AttributeRemover_2
AttributeRemover_2
    LIST_ATTRS = _list{}
    -> FeatureMerger_3 [SUPPLIER]

Bookmark: Leser og tolker XML for assosierte objekter
DuplicateFilter
    INPUT_ORDERED_CHOICE = No
    KEYATTR = vegobjektId typeId
    UNIQUE -> AttributeCreator_2
AttributeCreator_2
    ATTR_TABLE = SET_TO href = https://www.vegvesen.no/nvdb/api/v2/vegobjekter/@Value(typeId)/@Value(vegobjektId)
    -> NVDB_Leser_2 [_Input]
NVDB_Leser_2
    NESTE.HREF = @Value(href)
    -> ListExploder_2
    -> FeatureMerger_4 [REQUESTOR]

Bookmark: Lager assosiasjonslister med xlink_href
ListExploder_2
    ATTR_ACCUM_MODE = Merge Incoming List
    INDEX_ATTR = _element_index
    LIST_ATTR = assosiasjoner{}
    ATTR_CONFLICT_RES = Use Incoming List
    ELEMENTS -> AttributeKeeper_3
AttributeKeeper_3
    KEEP_ATTRS = vegobjektId,typeId,identifikasjon.Identifikasjon.navnerom,identifikasjon.Identifikasjon.lokalId,identifikasjon.Identifikasjon.versjonId
    -> Joiner_2
Joiner_2
    CSV__IN_SEPARATOR = ;
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    ATTR_ACCUM_MODE = Merge Joined
    CSV__GROUP_BY_DATASET = no
    DATASET = https://raw.githubusercontent.com/jetgeo/NVDBGML/master/XSD/NVDB_ftMapping.csv
    CSV__ALLOW_SPACES_IN_COLUMN_NAMES = yes
    ATTR_CONFLICT_RES = Use Original
    CSV__STRIP_QUOTES = yes
    CSV__IN_FIELD_NAMES = YES
    JOIN_KEYS = typeId ftid
    ADDED_FIELDS = name
    CSV__FIELD_NAMES_AFTER_HEADER = no
    CSV__DUPLICATE_DELIMS = no
    CSV__SCHEMA_WITH_COL_NAMES = ftid,number,4,0,name,char,23,
    CSV_SCAN_MAX_FEATURES = 1000
    FORMAT = CSV
    CSV__SKIP_FOOTER = 0
    MATCH_MULTIPLE_DISPLAY = Create a feature for each match
    TABLE = CSV
    CSV__SCHEMA = number,4,0,char,23,
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    MATCH_RULE_DISPLAY = Match All (1:M)
    JOINED -> StringConcatenator_2
StringConcatenator_2
    VAL_ATTR = xlink_href
    ACTION = Create New Attribute
    PARM_LINE = @Value(name).gml#$(namespace).@Value(vegobjektId)_0
    -> ListBuilder_2
ListBuilder_2
    LIST_NAME = _list
    GRP_BY = name identifikasjon.Identifikasjon.navnerom identifikasjon.Identifikasjon.lokalId identifikasjon.Identifikasjon.versjonId
    -> PythonCaller_2
PythonCaller_2
    PYTHONSYMBOL = processFeature
    PYTHONSOURCE:
      import fme
      import fmeobjects

      def processFeature(feature):
          anames= feature.getAllAttributeNames()
          lname = "blank"
          #find name attribute value
          for aname in anames:
              if aname == "name":
                  lname = feature.getAttribute(aname)
          #find list attributes and rename/copy to new name
          if lname != "blank":
              for aname in anames:
                  if aname.startswith("_list{"):
                      newAname=aname.replace("_list{","assosiert"+lname+"{")
                      aval = feature.getAttribute(aname)
                      feature.setAttribute(newAname, aval)
    -> AttributeRemover_3
AttributeRemover_3
    LIST_ATTRS = _list{}
    -> FeatureMerger_4 [SUPPLIER]

Bookmark: Assosierte objekter
FeatureMerger_4
    ATTR_CONFLICT_RES = Use Requestor
    JOIN_KEYS = @Value(identifikasjon.Identifikasjon.lokalId) @Value(identifikasjon.Identifikasjon.lokalId) AUTO
    ATTR_ACCUM_MODE = Merge Supplier
    IGNORE_NULLS = No
    SUPPLIERS_FIRST = No
    GEOM_TYPE = Build Polygons
    REJECT_NULL_MISSING_KEYS = No
    CONNECT_Z_MODE = First Wins
    PROCESS_DUPS = Yes
    MERGE_TYPE = Attributes Only
    MERGED -> SchemaMapper
    NOT_MERGED -> SchemaMapper

Bookmark: Oversetter til GML-verdier og -navn
Note: Oversetter tillatte verdier til GML-verdier
SchemaMapper
    CSV__SCHEMA = number,6,0,number,6,0,char,29,,char,34,
    ROW_ID_ATTR = _schemamapper_row_ids
    CSV__SKIP_LINES = 1
    MAP_ATTRS = enid ptid name
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    IDXDESTCOL = ""
    CSV__DUPLICATE_DELIMS = no
    CSV__STRIP_QUOTES = yes
    CSV__IN_FIELD_NAMES = YES
    IDXSOURCEATTR = fme_feature_type
    CSV_SCAN_MAX_FEATURES = 1000
    CSV__IN_SEPARATOR = ;
    IDXDESTATTR = fme_feature_type
    CSV__SCHEMA_WITH_COL_NAMES = ptid,number,6,0,enid,number,6,0,name,char,29,,fullname,char,34,
    CSV__ALLOW_SPACES_IN_COLUMN_NAMES = yes
    IDXSOURCECOL = ""
    FORMAT = CSV
    CSV__FIELD_NAMES_AFTER_HEADER = no
    MATCH_ATTRS = ptid enid
    DATASET = https://raw.githubusercontent.com/jetgeo/NVDBGML/master/XSD/NVDB_enMapping.csv
    CSV__SKIP_FOOTER = 0
    CSV__GROUP_BY_DATASET = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    MAPPED -> SchemaMapper_2
    UNMAPPED -> SchemaMapper_2
Note: Oversetter egenskapsnavn til GML-navn
SchemaMapper_2
    CSV__SCHEMA = char,17,,number,3,0,number,6,0,char,22,
    ROW_ID_ATTR = _schemamapper_row_ids
    CSV__SKIP_LINES = 1
    MAP_ATTRS = ptid name """"""
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXDESTCOL = ""
    CSV__DUPLICATE_DELIMS = no
    CSV__STRIP_QUOTES = yes
    CSV__IN_FIELD_NAMES = YES
    IDXSOURCEATTR = fme_feature_type
    CSV_SCAN_MAX_FEATURES = 1000
    CSV__IN_SEPARATOR = ;
    IDXDESTATTR = fme_feature_type
    CSV__SCHEMA_WITH_COL_NAMES = ft_attr,char,17,,ftid,number,3,0,ptid,number,6,0,name,char,22,
    CSV__ALLOW_SPACES_IN_COLUMN_NAMES = yes
    IDXSOURCECOL = ""
    FORMAT = CSV
    CSV__FIELD_NAMES_AFTER_HEADER = no
    MATCH_ATTRS = ft_attr ftid
    DATASET = https://raw.githubusercontent.com/jetgeo/NVDBGML/master/XSD/NVDB_ptMapping.csv
    CSV__SKIP_FOOTER = 0
    CSV__GROUP_BY_DATASET = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    MAPPED -> NullAttributeMapper_3
    UNMAPPED -> NullAttributeMapper_3
NullAttributeMapper_3
    NULL_TREATMENT = Missing
    SOURCE_ATTR_VAL = Empty Null
    ATTRCHOICE = All Attributes
    -> SchemaMapper_3
Note: Oversetter objekttypenavn til GML-navn
SchemaMapper_3
    CSV__SCHEMA = number,3,0,char,18,
    ROW_ID_ATTR = _schemamapper_row_ids
    CSV__SKIP_LINES = 1
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXDESTCOL = name
    CSV__DUPLICATE_DELIMS = no
    CSV__STRIP_QUOTES = yes
    CSV__IN_FIELD_NAMES = YES
    IDXSOURCEATTR = fme_feature_type
    CSV_SCAN_MAX_FEATURES = 1000
    CSV__IN_SEPARATOR = ;
    IDXDESTATTR = fme_feature_type
    CSV__SCHEMA_WITH_COL_NAMES = ftid,number,3,0,name,char,18,
    CSV__ALLOW_SPACES_IN_COLUMN_NAMES = yes
    IDXSOURCECOL = ftid
    FORMAT = CSV
    CSV__FIELD_NAMES_AFTER_HEADER = no
    DATASET = https://raw.githubusercontent.com/jetgeo/NVDBGML/master/XSD/NVDB_ftMapping.csv
    CSV__SKIP_FOOTER = 0
    CSV__GROUP_BY_DATASET = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    MAPPED -> AttributeExposer
    UNMAPPED -> AttributeExposer

Bookmark: Definerer geometriegenskaper
AttributeExposer
    ATTR_LIST = posisjon,senterlinje
    -> GeometryFilter
GeometryFilter
    BREAK_AGG = No
    GEOM_PORT_NAMES = Point Line Area
    POINT -> GeometryPropertySetter
    LINE -> GeometryPropertySetter_4
    AREA -> GeometryPropertySetter_3
GeometryPropertySetter
    OVERWRITE_CHOICE = Yes
    GEOM_NAME_FIELD = posisjon
    SETTYPE_PARAM = Geometry Name
    SET -> GeometryPropertySetter_SET
GeometryPropertySetter_4
    OVERWRITE_CHOICE = Yes
    GEOM_NAME_FIELD = senterlinje
    SETTYPE_PARAM = Geometry Name
    SET -> AttributeRemover
AttributeRemover
    REMOVE_ATTRS = posisjon
    -> GeometryPropertySetter_SET
GeometryPropertySetter_3
    OVERWRITE_CHOICE = Yes
    GEOM_NAME_FIELD = område
    SETTYPE_PARAM = Geometry Name
    SET -> GeometryPropertySetter_SET

FME custom transformer NVDB_Leser
Leser og tolker data fra NVDB-API

Parameters:
- NESTE.HREF = @Value(neste.href)   # neste.href

_Input (input)
    -> HTTPCaller_2
Loop (input)
    -> HTTPCaller_2
Note: Kan det defineres at et element SKAL blli en liste? Vil i så fall kunne forenkle koden i NVDBTranslator mye. / Se under cardinality under dokumentasjon i XML Fragmenter / https://knowledge.safe.com/idea/36634/better-and-more-consistent-support-for-listscollec.html / cardinality="*/*{?}/+{}"
HTTPCaller_2
    USE_COOKIES = No
    RESPONSE_HEADER_LIST_ATTR = _headers
    TRANSFER_TIMEOUT_LENGTH = 90
    FOLLOW_REDIRECTS = Yes
    TARGET_ATTR = _url_contents
    VERIFY_SSL_CERTIFICATES = Yes
    ERROR_ATTR = _error
    TARGET_URL = @Value(neste.href)
    HTTP_METHOD = GET
    CUSTOM_HEADERS = Accept;application/vnd.vegvesen.nvdb-v2+xml
    CONNECTION_TIMEOUT_LENGTH = 60
    STATUS_CODE_ATTR = _http_status_code
    TARGET_ATTR_ENCODING = auto-detect
    SAVE_FILE = Attribute
    -> XMLFragmenter_2
    -> XMLFragmenter
Note: Deler opp i en XML pr vegobjekt
XMLFragmenter
    ATTRIBUTE_XML = _url_contents
    EMBEDDED_EXPRESSIONS = vegobjekt
    MERGE_ATTRS = No
    NEW_ATTRIBUTES = id geometri.wkt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    XML_SOURCE_TYPE = Attribute with XML document
    FRAGMENTS -> NVDBTranslator
Note: Oversetter fra NVDB-API-XML
NVDBTranslator: PythonCaller
    PYTHONSYMBOL = extractNVDB_XML
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg
    PYTHONSOURCE:
      import fme
      import fmeobjects

      def extractNVDB_XML(feature):

          ns=FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute('lineærPosisjon{%d}.LineærPosisjonStrekning.nettverkselement.xlink_href' % i, 'Veglenker.gml#' + ns + '.rl.' + v)
                          v = str(feature.getAttribute('lokasjon.stedfestinger.stedfesting.fra_posisjon'))
                          if v != 'None':
                              feature.setAttribute('lineærPosisjon{%d}.LineærPosisjonStrekning.fraPosisjon' % i, v)
                          v = str(feature.getAttribute('lokasjon.stedfestinger.stedfesting.til_posisjon'))
                          if v != 'None':
                              feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                          feature.setAttribute('lineærPosisjon{%d}.LineærPosisjonStrekning.lineærReferanseMetode' % i, 'normalisert')

                      else:
                          # Punktstedfesting
                          v = str(feature.getAttribute('lokasjon.stedfestinger.stedfesting.veglenkeid'))
                          if v != 'None':
                              feature.setAttribute('lineærPosisjon{%d}.LineærPosisjonPunkt.nettverkselement.xlink_href' % i, 'Veglenker.gml#' + ns + '.rl.' + v)

                          v = str(feature.getAttribute('lokasjon.stedfestinger.stedfesting.posisjon'))
                          if v != 'None':
                              feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)
                          feature.setAttribute('lineærPosisjon{%d}.LineærPosisjonPunkt.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute('lineærPosisjon{%d}.LineærPosisjonStrekning.nettverkselement.xlink_href' % i, 'Veglenker.gml#' + ns + '.rl.' + v)

                      v = str(feature.getAttribute('lokasjon.stedfestinger.stedfesting{%d}.fra_posisjon' % i))
                      if v != 'None':
                          feature.setAttribute('lineærPosisjon{%d}.LineærPosisjonStrekning.fraPosisjon' % i, v)

                      v = str(feature.getAttribute('lokasjon.stedfestinger.stedfesting{%d}.til_posisjon' % i))
                      if v != 'None':
                          feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                      feature.setAttribute('lineærPosisjon{%d}.LineærPosisjonStrekning.lineærReferanseMetode' % i, 'normalisert')

                  else:
                      # Punktstedfesting
                      v = str(feature.getAttribute('lokasjon.stedfestinger.stedfesting{%d}.veglenkeid' % i))
                      if v != 'None':
                          feature.setAttribute('lineærPosisjon{%d}.LineærPosisjonPunkt.nettverkselement.xlink_href' % i, 'Veglenker.gml#' + ns + '.rl.' + v)

                      v = str(feature.getAttribute('lokasjon.stedfestinger.stedfesting{%d}.posisjon' % i))
                      if v != 'None':
                          feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)
                      feature.setAttribute('lineærPosisjon{%d}.LineærPosisjonPunkt.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    -> GeometryReplacer
Note: Geometri
GeometryReplacer
    OGC_WKT_PRECISION_DISPLAY = 64-bit
    REMOVE_ATTRIBUTE = Yes
    SOURCE = @Value(geometri)
    KIND_LONG = OGC Well Known Text
    -> CoordinateSystemSetter
    -> CoordinateSystemSetter_2
    -> 3DForcer
3DForcer
    ZVALATTR = NaN
    KEEPZVAL = Yes
    -> CoordinateSystemSetter_3
CoordinateSystemSetter_3
    COORDSYS = EPSG:6173
    -> Deaggregator
CoordinateSystemSetter [off]
    COORDSYS = @Value(epsg)
    -> Deaggregator
CoordinateSystemSetter_2 [off]
    COORDSYS = EPSG:6173
    -> Deaggregator
XMLFragmenter_2
    ATTRIBUTE_XML = _url_contents
    EMBEDDED_EXPRESSIONS = side/metadata
    MERGE_ATTRS = No
    NEW_ATTRIBUTES = returnert neste.href
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    XML_SOURCE_TYPE = Attribute with XML document
    FRAGMENTS -> TestFilter
TestFilter
    TEST_LIST = BOOL_OP,OR,COMPOSITE_TEST,<Unused>,TEST_CLAUSE,"TEST @Value(returnert) != 0",Flere
    DEFAULT_VALUE = <UNFILTERED>
    Flere -> Loop (output)
Loop (output)

Bookmark: Splitter multigeometrier
Deaggregator
    SPLIT_COMPOSITES = No
    EXPLODE_INSTANCES = No
    ID_SELECTION = ID and Parent ID
    GEOM_NAME_FIELD = _geometry_name
    PARENT_ID_ATTR = _hierarchy_parent_id
    ID_ATTR = _hierarchy_id
    LIST_ATTR_MODE_LOOKUP = LEAN
    MODE = Flatten One Level
    CHILD_ID_ATTR = _hierarchy_child_id_list
    PART_NUMBER_FIELD = _part_number
    COPY_ATTR = Every Node
    DEAGGREGATED -> NullAttributeMapper
NullAttributeMapper
    NULL_TREATMENT = New Value
    SOURCE_ATTR_VAL = Null Empty "Missing (Selected Attributes Only)"
    ATTRLIST = _part_number
    ATTRCHOICE = Selected Attributes
    NEW_VALUE = 0
    -> StringConcatenator
StringConcatenator
    VAL_ATTR = gml_id
    ACTION = Create New Attribute
    PARM_LINE = @Value(gml_id)_@Value(_part_number)
    -> Output (output)
Output (output)
