FME workspace 20180713_GML2API_Lillehammer.fmw

Parameters:
- omrNvn = 501   # Område
- wFolder = C:\DATA\GitHub\GLA\Data   # Arbeidsmappe
- vegkategori = K   # Vegkategori
- SourceDataset_GML_3 = C:\DATA\GitHub\GLA\Data\501\Belysningstrekning_Kabel_Lillehammer.gml   # Source Geography Markup Language (GML) File(s)
- omr = kommune   # Områdetype
- DakatVersjon = 2.07   # Datakatalogversjon

Readers:
- GML_1: GML from $(SourceDataset_GML_3)

Writers:
- TEXTLINE_1: TEXTLINE to $(wFolder)\XML\Belysningsdata.xml

Tennpunkt (reader GML_1) [off]
    attributes: driftsattår xml_decimal(5,0), driftsmerking xml_char(9), endringsflagg.Endringsflagg.tidspunktEndring xml_char(11), endringsflagg.Endringsflagg.typeEndring xml_char(2), identifikasjon.Identifikasjon.lokalId xml_char(6), identifikasjon.Identifikasjon.navnerom xml_char(20), kvalitet.Posisjonskvalitet.målemetode xml_decimal(3,0), kvalitet.Posisjonskvalitet.nøyaktighet xml_decimal(3,0), kvalitet.Posisjonskvalitet.synbarhet xml_decimal(2,0)
    -> Reprojector
Belysningspunkt (reader GML_1) [off]
    attributes: bruksområde xml_char(17), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), plassering xml_char(8), strømtilførselKategori xml_char(10), vedlikeholdsansvarlig xml_char(8)
    -> Reprojector
Lysarmatur (reader GML_1) [off]
    attributes: driftsattår xml_decimal(5,0), driftsmerking xml_char(9), effekt xml_decimal(4,0), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), lyskildeType xml_char(17), produktnavnArmatur xml_char(12), produsentnavnArmatur xml_char(14), vedlikeholdsansvarlig xml_char(8)
    -> Reprojector
Lysmast (reader GML_1) [off]
    attributes: bruksområde xml_char(4), byggeår xml_decimal(5,0), driftsmerking xml_char(9), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(3,0), kvalitet.Posisjonskvalitet.synbarhet xml_decimal(2,0), type xml_char(9), utligger xml_char(3), vedlikeholdsansvarlig xml_char(8)
    -> Reprojector
Belysningsstrekning (reader GML_1)
    attributes: bruksområde xml_char(17), byggeår xml_decimal(5,0), eier xml_char(8), eierNavn xml_char(20), endringsflagg.Endringsflagg.tidspunktEndring xml_char(11), endringsflagg.Endringsflagg.typeEndring xml_char(2), fjernstyring xml_char(3), identifikasjon.Identifikasjon.lokalId xml_char(8), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), type xml_char(18), vedlikeholdsansvarlig xml_char(8)
    -> Reprojector
Kabel (reader GML_1)
    attributes: antall xml_decimal(2,0), bruksområde xml_char(22), driftsattår xml_decimal(5,0), eier xml_char(8), eierNavn xml_char(20), endringsflagg.Endringsflagg.tidspunktEndring xml_char(11), endringsflagg.Endringsflagg.typeEndring xml_char(2), identifikasjon.Identifikasjon.lokalId xml_char(7), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), vedlikeholdsansvarlig xml_char(8)
    -> Reprojector
Reprojector
    DEST = ETRS89.UTM-33N
    INTERPOLATION_TYPE_NAME = Nearest Neighbor
    RASTER_CELL_SIZE = Preserve Cells
    RASTER_TOLERANCE = 0.0
    SOURCE = Read from feature
    REPROJECTED -> AttributeExposer_3
AttributeExposer_3
    ATTR_LIST = fme_feature_type
    -> DateFormatter
    -> LengthCalculator
DateFormatter
    DATE_ATTR = driftsattår
    FMT = %Y
    INVALID_DATE_VALUE = _FME_NO_OP_
    SRCFMT = Unknown - Automatic Detection
    -> org
    -> AttributeManager
org: Inspector
    TACKATTRS = fme_feature_type
AttributeManager
    ATTR_TABLE = SET_TO objekttype = @Value(fme_feature_type)
    -> SchemaMapper
    -> Vegnettposisjon
Note: Posisjon i vegnettet
Vegnettposisjon
    vegkategori = $(vegkategori)
    -> TestFilter
Note: Skiller melllom nye objekter og objekter som skal endres
TestFilter
    DEFAULT_VALUE = Endring
    TEST_LIST = BOOL_OP,OR,COMPOSITE_TEST,<Unused>,TEST_CLAUSE,"TEST @Value(endringsflagg.Endringsflagg.typeEndring) != E",Ny
    Ny -> SchemaMapper_2
    Endring -> AttributeRemover
AttributeRemover
    REMOVE_ATTRS = identifikasjon.Identifikasjon.navnerom,identifikasjon.Identifikasjon.lokalId
    -> NeighborFinder [BASE]
Note: Kobler endirngsobjekter til eksisterende fra NVDB
NeighborFinder
    ATTR_ACCUM_MODE = Merge Candidate
    ATTR_CONFLICT_RES = Use Base
    CANDIDATES_FIRST = No
    GROUP_BY = fme_feature_type
    INSERT_VERTEX = No
    K = 1
    MAX = 10
    MEASURE_TYPE = Continuous
    MODE = Bases and Candidates
    TREAT_POLYGON_AS = Lines
    MATCHED -> SchemaMapper_2
    UNMATCHED_BASE -> AttributeManager_3
    <REJECTED> -> NeighborFinder__Rejected_
Mapped: Inspector
    TACKATTRS = endringsflagg.Endringsflagg.typeEndring fme_feature_type
AttributeManager_2
    ATTR_TABLE = SET_TO assosiasjoner.antall = 0
    -> Counter_3
Counter_3
    CNT_ATTR = tempId
    DOMAIN = counter
    SCOPE = Global
    START = 1
    -> NullAttributeMapper
NullAttributeMapper
    ATTRCHOICE = All Attributes
    NULL_TREATMENT = Missing
    OTHER_VALUE = 0
    SOURCE_ATTR_VAL = Null Empty "Missing (Selected Attributes Only)"
    -> AttributeExploder
    -> FeatureMerger_5 [REQUESTOR]
Note: Kobler liste med egenskaper til objektet
FeatureMerger_5
    ATTR_ACCUM_MODE = Merge Supplier
    ATTR_CONFLICT_RES = Use Requestor
    CLEANING_TOLERANCE = None
    IGNORE_NULLS = No
    JOIN_KEYS = @Value(tempId) @Value(tempId) AUTO
    MERGE_TYPE = Attributes Only
    PROCESS_DUPS = No
    REJECT_NULL_MISSING_KEYS = No
    SUPPLIERS_FIRST = No
    MERGED -> AttributeManager_12
Note: Tilpasninger på vegObjektnivå
AttributeManager_12
    ATTR_TABLE:
      SET_TO vegObjekt.typeId = @Value(fme_feature_type)
      SET_TO vegObjekt.tempId = FME_CONDITIONAL:DEFAULT_VALUE'_FME_NO_OP_'BOOL_OP;OR;COMPOSITE_TEST;<Unused>;TEST @Value(endringsflagg.Endringsflagg.typeEndring) = N'@Value(tempId)'FME_NUM_CONDITIONS2___
      SET_TO vegObjekt.nvdbId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
      SET_TO vegObjekt.versjon = FME_CONDITIONAL:DEFAULT_VALUE'_FME_NO_OP_'BOOL_OP;OR;COMPOSITE_TEST;<Unused>;TEST @Value(endringsflagg.Endringsflagg.typeEndring) = E'@Value(identifikasjon.Identifikasjon.versjonId)'FME_NUM_CONDITIONS2___
    -> assosiasjonXML_2 [ROOT] [off]
    -> NullAttributeMapper_2
Note: Lager assosiasjons-XML for objektet, til senere bruk
assosiasjonXML_2: XMLTemplater
    OUTPUT_XML_HEADER = No
    RESULT_ATTRIBUTE = assosiasjon.XML
    ROOT_QUERY_EXPR:
      {if( {fme:get-attribute("endringsflagg.Endringsflagg.typeEndring")}="E") then
      <nvdbId>{fme:get-attribute("vegObjekt.nvdbId")}</nvdbId>
      else
      <tempId>-{fme:get-attribute("vegObjekt.tempId")}</tempId>}
    VISIBLE_QUERY_VALIDATE = Yes
    -> AttributeFilter
Note: Eksisterende asosiasjoner til objekter som ikke er med i datasettet: / Uberørt av transaksjonen / Men: Kan det bli et problem med ulik stedfesting?
AttributeFilter
    ATTR_NAME = objekttype
    ATTR_VALUES = <Empty>,<Missing>,<Null>,<Unfiltered>,Belysningsstrekning,Belysningspunkt,Lysmast,Lysarmatur,Tennpunkt
    Belysningsstrekning -> SpatialRelator [Requestor]
    Belysningspunkt -> Bufferer
    Belysningspunkt -> SpatialRelator_2 [Requestor]
    Belysningspunkt -> SpatialRelator_3 [Requestor]
    Belysningspunkt -> SpatialRelator_4 [Requestor]
    Lysmast -> AttributeFilter_Lysmast_-__AttributeValueMapper
    Lysmast -> Bufferer_2
    Lysarmatur -> AttributeFilter_Lysmast_-__AttributeValueMapper
    Lysarmatur -> Bufferer_3
    Tennpunkt -> AttributeFilter_Lysmast_-__AttributeValueMapper
    Tennpunkt -> Bufferer_4
Bufferer
    ANGLE = 22.5
    CAP_STYLE = Round
    CORNER_STYLE = Round
    OFFSET = 1
    BUFFERED -> SpatialRelator [Supplier]
SpatialRelator
    AGGREGATE_HANDLING = Yes
    CALC_CARD = No
    CURVE_BOUNDARY_RULE_PARAM = Default Rule
    LIST_ATTRS_TO_INCLUDE = assosiasjon.XML
    LIST_NAME = assosiasjoner
    PREDICATES = INTERSECTS
    SUCCESS_ATTR = assosiasjoner.antall
    -> assosiasjonXML_6 [ROOT]
assosiasjonXML_6: XMLTemplater
    OUTPUT_XML_HEADER = No
    RESULT_ATTRIBUTE = assosiasjoner.XML
    ROOT_QUERY_EXPR:
      {if( {fme:get-attribute("endringsflagg.Endringsflagg.typeEndring")}="E") then
      <assosiasjon typeId="220026" operasjon="oppdater">
          {fme:get-list-attribute("assosiasjoner{}.assosiasjon.XML")}
      </assosiasjon>
      else
      <assosiasjon typeId="220026">
          {fme:get-list-attribute("assosiasjoner{}.assosiasjon.XML")}
      </assosiasjon>}
    VISIBLE_QUERY_VALIDATE = Yes
    -> TestFilter_2 [off]
Bufferer_2
    ANGLE = 22.5
    CAP_STYLE = Round
    CORNER_STYLE = Round
    OFFSET = 1
    BUFFERED -> SpatialRelator_2 [Supplier]
SpatialRelator_2
    AGGREGATE_HANDLING = Yes
    CALC_CARD = No
    CURVE_BOUNDARY_RULE_PARAM = Default Rule
    LIST_ATTRS_TO_INCLUDE = assosiasjon.XML
    LIST_NAME = assosiasjoner
    PREDICATES = INTERSECTS
    SUCCESS_ATTR = assosiasjoner.antall
    -> assosiasjonXML_3 [ROOT]
assosiasjonXML_3: XMLTemplater
    OUTPUT_XML_HEADER = No
    RESULT_ATTRIBUTE = assosiasjoner.XML
    ROOT_QUERY_EXPR:
      {if( {fme:get-attribute("endringsflagg.Endringsflagg.typeEndring")}="E") then
      <assosiasjon typeId="220027" operasjon="oppdater">
          {fme:get-list-attribute("assosiasjoner{}.assosiasjon.XML")}
      </assosiasjon>
      else
      <assosiasjon typeId="220027">
          {fme:get-list-attribute("assosiasjoner{}.assosiasjon.XML")}
      </assosiasjon>}
    VISIBLE_QUERY_VALIDATE = Yes
    -> TestFilter_2 [off]
Bufferer_3
    ANGLE = 22.5
    CAP_STYLE = Round
    CORNER_STYLE = Round
    OFFSET = 1
    BUFFERED -> SpatialRelator_3 [Supplier]
SpatialRelator_3
    AGGREGATE_HANDLING = Yes
    CALC_CARD = No
    CURVE_BOUNDARY_RULE_PARAM = Default Rule
    LIST_ATTRS_TO_INCLUDE = assosiasjon.XML
    LIST_NAME = assosiasjoner
    PREDICATES = INTERSECTS
    SUCCESS_ATTR = assosiasjoner.antall
    -> assosiasjonXML_4 [ROOT]
assosiasjonXML_4: XMLTemplater
    OUTPUT_XML_HEADER = No
    RESULT_ATTRIBUTE = assosiasjoner.XML
    ROOT_QUERY_EXPR:
      {if( {fme:get-attribute("endringsflagg.Endringsflagg.typeEndring")}="E") then
      <assosiasjon typeId="220028" operasjon="oppdater">
          {fme:get-list-attribute("assosiasjoner{}.assosiasjon.XML")}
      </assosiasjon>
      else
      <assosiasjon typeId="220028">
          {fme:get-list-attribute("assosiasjoner{}.assosiasjon.XML")}
      </assosiasjon>}
    VISIBLE_QUERY_VALIDATE = Yes
    -> TestFilter_2 [off]
Bufferer_4
    ANGLE = 22.5
    CAP_STYLE = Round
    CORNER_STYLE = Round
    OFFSET = 1
    BUFFERED -> SpatialRelator_4 [Supplier]
SpatialRelator_4
    AGGREGATE_HANDLING = Yes
    CALC_CARD = No
    CURVE_BOUNDARY_RULE_PARAM = Default Rule
    LIST_ATTRS_TO_INCLUDE = assosiasjon.XML
    LIST_NAME = assosiasjoner
    PREDICATES = INTERSECTS
    SUCCESS_ATTR = assosiasjoner.antall
    -> assosiasjonXML_5 [ROOT]
assosiasjonXML_5: XMLTemplater
    OUTPUT_XML_HEADER = No
    RESULT_ATTRIBUTE = assosiasjoner.XML
    ROOT_QUERY_EXPR:
      {if( {fme:get-attribute("endringsflagg.Endringsflagg.typeEndring")}="E") then
      <assosiasjon typeId="220560" operasjon="oppdater">
          {fme:get-list-attribute("assosiasjoner{}.assosiasjon.XML")}
      </assosiasjon>
      else
      <assosiasjon typeId="220560">
          {fme:get-list-attribute("assosiasjoner{}.assosiasjon.XML")}
      </assosiasjon>}
    VISIBLE_QUERY_VALIDATE = Yes
    -> TestFilter_2
Note: Etablere assosiasjoner basert på geometri: / - Belysningsstrekning til Belysningspunkt / - Belysningspunkt til Lysmast og Lysarmatur / Hardkoda, forbedringspotensliale. Antakelig vha Python-script
TestFilter_2
    DEFAULT_VALUE = <UNFILTERED>
    TEST_LIST = "BOOL_OP,OR,COMPOSITE_TEST,""""""<Unused>"""""",TEST_CLAUSE,TEST @Value(assosiasjoner.antall) > 0",HarAssosiasjoner
    HarAssosiasjoner -> StringReplacer_8
StringReplacer_8
    CASE = NO
    FIND_TEXT = &lt;
    NO_MATCH = _FME_NO_OP_
    REGEXP = NO
    REPLACE_TEXT = <
    SRC_ATTRS = assosiasjoner.XML
    -> StringReplacer_9
StringReplacer_9
    CASE = NO
    FIND_TEXT = &gt;
    NO_MATCH = _FME_NO_OP_
    REGEXP = NO
    REPLACE_TEXT = >
    SRC_ATTRS = assosiasjoner.XML
    -> Aggregator
Aggregator
    ACCUM_ATTRS_NAME = Use Attributes From One Feature
    AGGREGATE_TYPE = Homogeneous Collection (If Possible)
    GROUP_BY = tempId
    LIST_ATTRS_TO_INCLUDE = assosiasjoner.XML
    LIST_NAME = assosiasjoner
    MODE = Geometry - Assemble One Level
    ORDERED = No
    SEP = ,
    SUM = assosiasjoner.antall
    AGGREGATE -> NullAttributeMapper_2
AttributeFilter_Lysmast_-__AttributeValueMapper: Junction
    -> NullAttributeMapper_2 [off]
NullAttributeMapper_2
    ATTRCHOICE = Selected Attributes
    ATTRLIST = assosiasjoner.antall
    NEW_VALUE = 0
    NULL_TREATMENT = New Value
    SOURCE_ATTR_VAL = Null Empty "Missing (Selected Attributes Only)"
    -> StringFormatter
StringFormatter
    FORMAT = d
    SRC_ATTRS = assosiasjoner.antall
    -> AttributeValueMapper
Note: Geometriegenskap
Note: Håndtering av geometriegenskap må forbedres. Pr nå er denne "hardkoda" i AttributeValueMapper
AttributeValueMapper
    DIRECTION = Forward (Source To Destination)
    LUT = 86,4786,87,4787,88,4788,181,4838,481,4996
    SRC = fme_feature_type
    VAL_ATTR = _geometriegenskap
    -> vegObjektXML [ROOT]
vegObjektXML: XMLTemplater
    OUTPUT_XML_HEADER = No
    RESULT_ATTRIBUTE = vegObjekt.XML
    ROOT_QUERY_EXPR:
      {if( fme:has-attribute("vegObjekt.nvdbId")) then
          <vegObjekt typeId="{fme:get-attribute("vegObjekt.typeId")}" nvdbId="{fme:get-attribute("vegObjekt.nvdbId")}" versjon="{fme:get-attribute("vegObjekt.versjon")}">
              <egenskaper>
              {fme:get-list-attribute("egenskaper{}.egenskap.XML")}
              {if( fme:has-attribute("_geometry")) then
              <egenskap typeId="{fme:get-attribute("_geometriegenskap")}" operasjon="oppdater">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}

              <lokasjon operasjon="oppdater">
                  {fme:get-attribute("lokasjon")}
              </lokasjon>
          </vegObjekt>
      else
          <vegObjekt typeId="{fme:get-attribute("vegObjekt.typeId")}" tempId="-{fme:get-attribute("tempId")}">
              <egenskaper>
              {fme:get-list-attribute("egenskaper{}.egenskap.XML")}
              {if( fme:has-attribute("_geometry")) then
              <egenskap typeId="{fme:get-attribute("_geometriegenskap")}">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}
              <lokasjon>
                  {fme:get-attribute("lokasjon")}
              </lokasjon>
          </vegObjekt>}
    VISIBLE_QUERY_VALIDATE = Yes
    -> StringReplacer_3
ListBuilder_3
    GROUP_BY = endringsflagg.Endringsflagg.typeEndring
    LIST_NAME = vegObjektliste
    -> EndringssettXML [ROOT]
EndringssettXML: XMLTemplater
    OUTPUT_XML_HEADER = No
    RESULT_ATTRIBUTE = endringssett.XML
    ROOT_QUERY_EXPR:
        {if( {fme:get-attribute("endringsflagg.Endringsflagg.typeEndring")}="E") then
        <delvisOppdater>
          <vegObjekter>
          {fme:get-list-attribute("vegObjektliste{}.vegObjekt.XML")}
          </vegObjekter>
        </delvisOppdater>
        else if( {fme:get-attribute("endringsflagg.Endringsflagg.typeEndring")}="N") then
        <registrer>
          <vegObjekter>
          {fme:get-list-attribute("vegObjektliste{}.vegObjekt.XML")}
          </vegObjekter>
        </registrer>
        else ()}
    VISIBLE_QUERY_VALIDATE = Yes
    -> AttributeKeeper_7
ListBuilder_4
    LIST_NAME = endringsliste
    -> TimeStamper
TimeStamper
    FMT = ^Y-^m-^d
    TIME_ATTR = _timestamp
    -> EndringslisteXML [ROOT]
EndringslisteXML: XMLTemplater
    OUTPUT_XML_HEADER = No
    RESULT_ATTRIBUTE = endringsliste.XML
    ROOT_QUERY_EXPR:
      <endringssett xmlns="http://nvdb.vegvesen.no/apiskriv/domain/v2" effektDato="{fme:get-attribute("_timestamp")}" datakatalogversjon="$(DakatVersjon)">
      {fme:get-list-attribute("endringsliste{}.endringssett.XML")}
      </endringssett>
    VISIBLE_QUERY_VALIDATE = Yes
    -> StringReplacer
Sampler
    GROUP_BY = fme_feature_type
    RATE = 1
    SAMPLE_MODE = No
    SAMPLE_TYPE_LONG = Every Nth Feature
    SAMPLED -> AttributeRenamer_4
AttributeRenamer_4
    ATTR_TABLE = RENAME_SET_DEFAULT _xml_output > text_line_data
    -> text_line (writer TEXTLINE_1)
text_line (writer TEXTLINE_1)
    attributes: text_line_data buffer
NeighborFinder__Rejected_: Inspector
NVDB: Inspector
    TACKATTRS = fme_feature_type
FeatureReader__Rejected_: Inspector
LengthCalculator [off]
    DIM = 2
    LEN_ATTR = _length
    MULT = 1
    -> LengthCalculator_Output
LengthCalculator_Output: Inspector

Bookmark: Eksisterende objekter i NVDB
Note: Mapper objekttypenavn til VOT-ID vha mappingtabell ftMapping / - for å finne aktuellle objekttyper
SchemaMapper
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = number,3,0,char,18,
    CSV__SCHEMA_WITH_COL_NAMES = ftid,number,3,0,name,char,18,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = C:\DATA\GitHub\GLA\XSD\glabelysning_ftMapping.csv
    FORMAT = CSV
    IDXDESTATTR = fme_feature_type
    IDXDESTCOL = ftid
    IDXSOURCEATTR = fme_feature_type
    IDXSOURCECOL = name
    ROW_ID_ATTR = _schemamapper_row_ids
    TABLE = CSV
    MAPPED -> DuplicateFilter
DuplicateFilter
    INPUT_ORDERED_CHOICE = No
    KEYATTR = fme_feature_type
    UNIQUE -> WorkspaceRunner
    UNIQUE -> FeatureReader [INITIATOR]
Note: Eksporterer eksisterende fra NVDB til GML
WorkspaceRunner [off]
    BLOCKING = Yes
    WORKSPACE_FILE = C:\DATA\GitHub\NVDBGML\FME\NVDBAPI2GML_V2_2018.fmw
    WORKSPACE_PARAMETERS = ftID,@Value(fme_feature_type),omr,$(omr),omrNvn,$(omrNvn),gmlFolder,$(wFolder),dwnlAssObj,Nei
    SUCCEEDED -> FeatureReader [INITIATOR]
Note: Leser eksisterende NVDB-objekter fra GML
FeatureReader
    ATTR_ACCUM_MODE = Only Use Result
    COMBINE_GEOM = Use Result
    DATASET = $(wFolder)\$(omr)\$(omrNvn)\@Value(fme_feature_type)\@Value(objekttype).gml
    FORMAT = GML
    GML_ADD_GEOMETRIES_AS_XML_FRAGMENTS = NO
    GML_CACHE_XSD = yes
    GML_CLIP_TO_ENVELOPE = NO
    GML_CONTINUE_ON_GEOM_ERROR = yes
    GML_DISABLE_AUTOMATIC_READER_TYPE_SELECTION = NO
    GML_DISABLE_XML_NAMESPACE_PROCESSING = NO
    GML_ENFORCE_PATH_CONTINUITY_BY = SNAPPING_END_POINTS
    GML_FEATURE_TYPES_SCHEMA_MODE = XML_SCHEMA
    GML_FLATTEN_XML_FRAGMENTS = NO
    GML_IGNORE_APPLICATON_SCHEMA = no
    GML_MAP_ALL_SUBSTITUTABLE_PROPERTIES = YES
    GML_MAP_COMPLEX_PROPERTIES_AS = Nested Attributes
    GML_MAP_EMBEDDED_OBJECTS_AS = ATTRIBUTES
    GML_MAP_GEOMETRY_COLUMNS = YES
    GML_MAP_PREDEFINED_GML_PROPERTIES = NO
    GML_MULTI_VALUE_SIMPLE_PROPERTIES_AS_CSV = no
    GML_SKIP_SCHEMA_LOCATION_IN_DATASET = No
    GML_USE_OLD_READER = NO
    GML_USE_SEARCH_ENVELOPE = NO
    GML_VALIDATE_DATASET = no
    GML_XML_FRAGMENTS_AS_DOCUMENTS = YES
    INTERACT = <No Spatial Filter>
    OUTPUT_FEATURES_DISPLAY = Schema and Data Features
    <OTHER> -> AttributeExposer
    <REJECTED> -> FeatureReader__Rejected_
AttributeExposer
    ATTR_LIST = fme_feature_type,vegreferanse{}.Vegreferanse.vegkategori,identifikasjon.Identifikasjon.lokalId,identifikasjon.Identifikasjon.versjonId,lineærPosisjon{}.LineærPosisjonPunkt.nettverkselement.xlink_href
    -> ListSearcher
Note: Begrenser til objekter på valgt vegkategori
ListSearcher
    ATTR_VALUE = $(vegkategori)
    INDEX_ATTR = _list_index
    LIST_ATTR = vegreferanse{}.Vegreferanse.vegkategori
    SEARCH_TYPE = First exact match
    FOUND -> NVDB
    FOUND -> NeighborFinder [CANDIDATE]

Bookmark: Mapping til Datakatalog-IDer
Note: Setter endringstype = N for de som ikke blir kobla
AttributeManager_3
    ATTR_TABLE = SET_TO endringsflagg.Endringsflagg.typeEndring = N
    -> Endring_uten_eksisterende
    -> SchemaMapper_2
Note: Mapper objekttypenavn til VOT-ID vha mappingtabell ftMapping
SchemaMapper_2
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = number,3,0,char,18,
    CSV__SCHEMA_WITH_COL_NAMES = ftid,number,3,0,name,char,18,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = C:\DATA\GitHub\GLA\XSD\glabelysning_ftMapping.csv
    FORMAT = CSV
    IDXDESTATTR = fme_feature_type
    IDXDESTCOL = ftid
    IDXSOURCEATTR = fme_feature_type
    IDXSOURCECOL = name
    ROW_ID_ATTR = _schemamapper_row_ids
    TABLE = CSV
    MAPPED -> AttributeExposer_2
AttributeExposer_2
    ATTR_LIST = fme_feature_type
    -> SchemaMapper_3
Note: Mapper egenskapsnavn til ET-ID vha mappingtabell ptMapping
SchemaMapper_3
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = char,17,,number,4,0,number,6,0,char,43,
    CSV__SCHEMA_WITH_COL_NAMES = ft_attr,char,17,,ftid,number,4,0,ptid,number,6,0,name,char,43,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = C:\DATA\GitHub\GLA\XSD\glabelysning_ptMapping.csv
    FORMAT = CSV
    IDXDESTATTR = fme_feature_type
    IDXDESTCOL = ""
    IDXSOURCEATTR = fme_feature_type
    IDXSOURCECOL = ""
    MAP_ATTRS = name ptid $(FME_ASC_16)
    MATCH_ATTRS = ft_attr ftid
    ROW_ID_ATTR = _schemamapper_row_ids
    TABLE = CSV
    MAPPED -> SchemaMapper_4
Note: Oversetter tillatte verdier til NVDB-tekstverdier
SchemaMapper_4
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ;
    CSV__SCHEMA = number,6,0,number,6,0,char,29,,char,34,
    CSV__SCHEMA_WITH_COL_NAMES = ptid,number,6,0,enid,number,6,0,name,char,29,,fullname,char,34,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = C:\DATA\GitHub\GLA\XSD\glabelysning_enMapping.csv
    FORMAT = CSV
    IDXDESTATTR = fme_feature_type
    IDXDESTCOL = ""
    IDXSOURCEATTR = fme_feature_type
    IDXSOURCECOL = ""
    MAP_ATTRS = """""" ptid fullname
    MATCH_ATTRS = ptid name
    ROW_ID_ATTR = _schemamapper_row_ids
    TABLE = CSV
    MAPPED -> CoordinateRounder
    UNMAPPED -> AttributeExposer_4
    UNMAPPED -> CoordinateRounder
AttributeExposer_4 [off]
    ATTR_LIST = 1832
    -> AttributeManager_13
AttributeManager_13 [off]
    ATTR_TABLE = SET_TO 1832 = FME_CONDITIONAL:DEFAULT_VALUE'FME_NULL_VALUE'BOOL_OP;OR;COMPOSITE_TEST;<Unused>;TEST @Value(1832) = nei;TEST @Value(1832) = Nei'Nei'BOOL_OP;OR;COMPOSITE_TEST;<Unused>;TEST @Value(1832) = ja;TEST @Value(1832) = Ja'Ja'FME_NUM_CONDITIONS3___
    -> CoordinateRounder [off]
Endring_uten_eksisterende: Inspector
    TACKATTRS = fme_feature_type

Bookmark: Lager geometristreng
CoordinateRounder
    XPREC = 3
    YPREC = 3
    ZPREC = 3
    ROUNDED -> CoordinateConcatenator
CoordinateConcatenator
    COORDINATES_TO_INCLUDE_DIS = X Y Z
    COORD_ATTR = _coordinates
    COORD_DELIM = ,
    ELEMENT_DELIM = " "
    PRECISION = No
    -> StringReplacer_7
StringReplacer_7
    CASE = NO
    FIND_TEXT = " -99999"
    NO_MATCH = _FME_NO_OP_
    REGEXP = NO
    SRC_ATTRS = _coordinates
    -> GeometryFilter
GeometryFilter
    BREAK_AGG = No
    GEOM_PORT_NAMES = Point Line
    POINT -> StringConcatenator_2
    LINE -> StringConcatenator
StringConcatenator_2
    ACTION = Create New Attribute
    PARM_LINE = POINT(@Value(_coordinates))
    VAL_ATTR = _geometry
    -> StringConcatenator_2_OUTPUT_-__PythonCaller
StringConcatenator
    ACTION = Create New Attribute
    PARM_LINE = LINESTRING(@Value(_coordinates))
    VAL_ATTR = _geometry
    -> StringConcatenator_2_OUTPUT_-__PythonCaller
StringConcatenator_2_OUTPUT_-__PythonCaller: Junction
    -> PythonCaller
Note: Kvalitetsstreng
PythonCaller
    NEW_ATTRIBUTES = qualityString
    PYTHONSOURCE:
      import fmeobjects
      # Template Function interface:

      def setQuality(feature):
          qs=""
          qm = feature.getAttribute(u'kvalitet.Posisjonskvalitet.målemetode')
          qms=str(qm)
          if qms <> "None":
              qs=u"målemetode="+qms

          qm = feature.getAttribute(u'kvalitet.Posisjonskvalitet.nøyaktighet')
          qms=str(qm)
          if qms <> "None":
              qs=qs+u"; nøyaktighet="+qms

          qm = feature.getAttribute(u'kvalitet.Posisjonskvalitet.synbarhet')
          qms=str(qm)
          if qms <> "None":
              qs=qs+u"; synbarhet="+qms

          qm = feature.getAttribute(u'kvalitet.Posisjonskvalitet.målemetodeHøyde')
          qms=str(qm)
          if qms <> "None":
              qs=qs+u"; målemetodeHøyde="+qms

          qm = feature.getAttribute(u'kvalitet.Posisjonskvalitet.nøyaktighetHøyde')
          qms=str(qm)
          if qms <> "None":
              qs=qs+u"; nøyaktighetHøyde="+qms

          if qs <> "":
              feature.setAttribute(u'qualityString', 'srid=25833;'+qs+'; ')
    PYTHONSYMBOL = setQuality
    -> Mapped
    -> AttributeManager_2

Bookmark: Liste med egenskaper
AttributeExploder
    ATTR_NAME_LABEL = _attr_name
    ATTR_VALUE_LABEL = _attr_value
    EXPLODING_TYPE = Features
    KEEP_ATTRIBUTES = Yes
    KEEP_GEOMETRY = No
    -> AttributeKeeper_5
AttributeKeeper_5
    KEEP_ATTRS = endringsflagg.Endringsflagg.typeEndring,_attr_value,tempId,_attr_name
    -> AttributeValidator
AttributeValidator
    TABLE = _attr_name;TYPE;NUM
    PASSED -> AttributeManager_9
AttributeManager_9
    ATTR_TABLE:
      RENAME_SET_VALUE _attr_name > egenskap.typeId
      RENAME_SET_VALUE _attr_value > egenskap.verdi
      SET_TO egenskap.operasjon = FME_CONDITIONAL:DEFAULT_VALUE'_FME_NO_OP_'BOOL_OP;OR;COMPOSITE_TEST;<Unused>;TEST @Value(endringsflagg.Endringsflagg.typeEndring) = E'oppdater'FME_NUM_CONDITIONS2___
    -> egenskapXML [ROOT]
egenskapXML: XMLTemplater
    OUTPUT_XML_HEADER = No
    RESULT_ATTRIBUTE = egenskap.XML
    ROOT_QUERY_EXPR:
      {if( fme:has-attribute("egenskap.operasjon")) then
      <egenskap typeId="{fme:get-attribute("egenskap.typeId")}" operasjon="{fme:get-attribute("egenskap.operasjon")}">
          <verdi>{fme:get-attribute("egenskap.verdi")}</verdi>
      </egenskap>
      else
      <egenskap typeId="{fme:get-attribute("egenskap.typeId")}">
          <verdi>{fme:get-attribute("egenskap.verdi")}</verdi>
      </egenskap>}
    VISIBLE_QUERY_VALIDATE = Yes
    -> ListBuilder_2
ListBuilder_2
    GROUP_BY = tempId
    LIST_NAME = egenskaper
    -> FeatureMerger_5 [SUPPLIER]

Bookmark: Opprydding i tekst
StringReplacer_3
    CASE = NO
    FIND_TEXT = &lt;
    NO_MATCH = _FME_NO_OP_
    REGEXP = NO
    REPLACE_TEXT = <
    SRC_ATTRS = vegObjekt.XML
    -> StringReplacer_4
StringReplacer_4
    CASE = NO
    FIND_TEXT = &gt;
    NO_MATCH = _FME_NO_OP_
    REGEXP = NO
    REPLACE_TEXT = >
    SRC_ATTRS = vegObjekt.XML
    -> AttributeRemover_4
AttributeRemover_4
    LIST_ATTRS = egenskaper{}
    -> AttributeManager_4
AttributeManager_4
    NUM_PRIOR_FEATURES = 0
    NUM_SUBSEQUENT_FEATURES = 0
    -> ListBuilder_3

Bookmark: Opprydding
AttributeKeeper_7
    KEEP_ATTRS = endringsflagg.Endringsflagg.typeEndring,fme_feature_type,endringssett.XML
    -> StringReplacer_5
StringReplacer_5
    CASE = NO
    FIND_TEXT = &lt;
    NO_MATCH = _FME_NO_OP_
    REGEXP = NO
    REPLACE_TEXT = <
    SRC_ATTRS = endringssett.XML
    -> StringReplacer_6
StringReplacer_6
    CASE = NO
    FIND_TEXT = &gt;
    NO_MATCH = _FME_NO_OP_
    REGEXP = NO
    REPLACE_TEXT = >
    SRC_ATTRS = endringssett.XML
    -> ListBuilder_4

Bookmark: Opprydding
StringReplacer
    CASE = NO
    FIND_TEXT = &lt;
    NO_MATCH = _FME_NO_OP_
    REGEXP = NO
    REPLACE_TEXT = <
    SRC_ATTRS = endringsliste.XML
    -> StringReplacer_2
StringReplacer_2
    CASE = NO
    FIND_TEXT = &gt;
    NO_MATCH = _FME_NO_OP_
    REGEXP = NO
    REPLACE_TEXT = >
    SRC_ATTRS = endringsliste.XML
    -> XMLFormatter_2
XMLFormatter_2
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = Yes
    REPLACE_TABS_WITH_SPACES = no
    SCHEMALOC_CLEANUP = No
    TEXT_INDENT = no
    WHITESPACE_HANDLING = Preserve all whitespace
    XML_ATTR_TEXT = endringsliste.XML
    XML_INPUT_TYPE = Attribute Specifying XML Text
    XML_OUTPUT_ATTR = _xml_output
    XML_OUTPUT_TYPE = Attribute
    PASSED -> Sampler [off]
    PASSED -> AttributeRenamer_4

FME custom transformer Vegnettposisjon
Finner prosisjon i vegnettet

Parameters:
- vegkategori = K   # Vegkategori

Input (input)
    -> Counter
Counter
    CNT_ATTR = _count
    DOMAIN = counter
    SCOPE = Global
    START = 0
    -> CoordinateCounter
    -> FeatureMerger [REQUESTOR]
ListBuilder
    GROUP_BY = _coordcount _count ReflinkOID
    LIST_ATTRS_TO_INCLUDE = Measure _element_index
    LIST_NAME = _list
    -> ListRangeExtractor
ListRangeExtractor
    MAX = _max
    MIN = _min
    SRC_LIST = _list{}.Measure
    -> AttributeRemover
AttributeRemover
    LIST_ATTRS = _list{}
    -> AttributeManager
AttributeManager
    ATTR_TABLE:
      SET_TO _posisjon = FME_CONDITIONAL:DEFAULT_VALUE'_FME_NO_OP_'BOOL_OP;OR;COMPOSITE_TEST;<Unused>;TEST @Value(_min) = @Value(_max)'@Value(_min)'FME_NUM_CONDITIONS2___
      SET_TO _fraPosisjon = FME_CONDITIONAL:DEFAULT_VALUE'_FME_NO_OP_'BOOL_OP;OR;COMPOSITE_TEST;<Unused>;TEST @Value(_min) != @Value(_max)'@Value(_min)'FME_NUM_CONDITIONS2___
      SET_TO _tilPosisjon = FME_CONDITIONAL:DEFAULT_VALUE'_FME_NO_OP_'BOOL_OP;OR;COMPOSITE_TEST;<Unused>;TEST @Value(_min) != @Value(_max)'@Value(_max)'FME_NUM_CONDITIONS2___
      REMOVE _max
      REMOVE _min
    -> TestFilter_3
TestFilter_3
    DEFAULT_VALUE = <UNFILTERED>
    TEST_LIST:
      BOOL_OP,AND,COMPOSITE_TEST,<Unused>,TEST_CLAUSE,"TEST @Value(_coordcount) > 1
      TEST @Value(_posisjon) ATTRIBUTE_HAS_VALUE """"",PunktPosIStrekning
    <UNFILTERED> -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(_count) @Value(_count) AUTO
    LIST_ATTRS_TO_INCLUDE = ReflinkOID _fraPosisjon _posisjon _tilPosisjon
    LIST_NAME = _posList
    MERGE_TYPE = Attributes Only
    PROCESS_DUPS = Yes
    REJECT_NULL_MISSING_KEYS = No
    SUPPLIERS_FIRST = No
    MERGED -> AttributeManager_3
AttributeManager_3
    ATTR_TABLE = SET_TO lokasjon = FME_CONDITIONAL:DEFAULT_VALUE'_FME_NO_OP_'BOOL_OP;OR;COMPOSITE_TEST;<Unused>;TEST @Value(_posisjon) ATTRIBUTE_HAS_VALUE _FME_BLANK_STRING_'<punkt lenkeId="@Value(ReflinkOID)" posisjon="@Value(_posisjon)"  />'BOOL_OP;AND;COMPOSITE_TEST;<Unused>;TEST @Value(_fraPosisjon) ATTRIBUTE_HAS_VALUE _FME_BLANK_STRING_;TEST @Value(_tilPosisjon) ATTRIBUTE_HAS_VALUE _FME_BLANK_STRING_'<linje lenkeId="@Value(ReflinkOID)" fra="@Value(_fraPosisjon)" til="@Value(_tilPosisjon)" />'FME_NUM_CONDITIONS3___
    -> Output (output)
Output (output)

Bookmark: Finner posisjon i vegnettet
CoordinateCounter
    CNT_ATTR = _coordcount
    -> CoordinateExtractor
Note: Alle knekkpunkt
CoordinateExtractor
    LIST_NAME = _indices
    MODE = All Coordinates
    -> ListExploder
ListExploder
    ATTR_ACCUM_MODE = Merge List Attributes
    ATTR_CONFLICT_RES = Use List Attribute Values
    INDEX_ATTR = _element_index
    LIST_ATTR = _indices{}
    ELEMENTS -> AttributeCreator_2
AttributeCreator_2
    ATTR_TABLE = SET_TO httpReq = https://www.vegvesen.no/nvdb/api/v2/posisjon.xml?nord=@Value(y)&ost=@Value(x)&vegreferanse=$(vegkategori)
    -> HTTPCaller_2
Note: Finner posisjon for representasjonspunktet, med filter på vegkategori
HTTPCaller_2
    CONNECTION_TIMEOUT_LENGTH = 60
    ERROR_ATTR = _error
    FILE_TYPE = <Auto Detect from HTTP Headers>
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(httpReq)
    TRANSFER_TIMEOUT_LENGTH = 90
    USE_COOKIES = No
    VERIFY_SSL_CERTIFICATES = Yes
    -> XMLFlattener_2
    <Rejected> -> AttributeCreator_3
XMLFlattener_2
    ATTRIBUTE_XML = _response_body
    EMBEDDED_EXPRESSIONS = veglenke
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = id posisjon
    XML_SOURCE_TYPE = Attribute with XML document
    -> TestFilter
Note: Ekstra kontroll på at objektene har fått posisjon. Får en del tilfeller der det ikke gis feil, men bare tomt svar
TestFilter
    DEFAULT_VALUE = <UNFILTERED>
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    HarPosisjon -> XMLFlattener_5
    <UNFILTERED> -> AttributeCreator_3
XMLFlattener_5
    ATTRIBUTE_XML = _response_body
    EMBEDDED_EXPRESSIONS = vegreferanse
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = fylke kommune kategori status nummer hp meter kortform
    XML_SOURCE_TYPE = Attribute with XML document
    -> AttributeManager_2
AttributeCreator_3
    ATTR_TABLE = SET_TO httpReq = https://www.vegvesen.no/nvdb/api/v2/posisjon.xml?nord=@Value(y)&ost=@Value(x)
    -> HTTPCaller_3
Note: Finner posisjon for representasjonspunktet, uten filter på vegkategori
HTTPCaller_3
    CONNECTION_TIMEOUT_LENGTH = 60
    ERROR_ATTR = _error
    FILE_TYPE = <Auto Detect from HTTP Headers>
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(httpReq)
    TRANSFER_TIMEOUT_LENGTH = 90
    USE_COOKIES = No
    VERIFY_SSL_CERTIFICATES = Yes
    -> XMLFlattener_4
    <Rejected> -> IngenPosisjon
XMLFlattener_4
    ATTRIBUTE_XML = _response_body
    EMBEDDED_EXPRESSIONS = veglenke
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = id posisjon
    XML_SOURCE_TYPE = Attribute with XML document
    -> TestFilter_2
Note: Ekstra kontroll på at objektene har fått posisjon. Får en del tilfeller der det ikke gis feil, men bare tomt svar
TestFilter_2
    DEFAULT_VALUE = <UNFILTERED>
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    HarPosisjon -> XMLFlattener_3
    <UNFILTERED> -> IngenPosisjon
XMLFlattener_3
    ATTRIBUTE_XML = _response_body
    EMBEDDED_EXPRESSIONS = vegreferanse
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = fylke kommune kategori status nummer hp meter kortform
    XML_SOURCE_TYPE = Attribute with XML document
    -> AnnenVegkategori
    -> AttributeManager_2
AttributeManager_2
    ATTR_TABLE:
      REMOVE httpReq
      REMOVE _error
      REMOVE _headers{}.name
      REMOVE _headers{}.value
      REMOVE _response_body
      REMOVE _http_status_code
      RENAME_SET_VALUE id > ReflinkOID
      RENAME_SET_VALUE posisjon > Measure
      REMOVE fylke
      REMOVE kommune
      RENAME_SET_VALUE kategori > vegident.Vegident.vegkategori
      RENAME_SET_VALUE status > vegident.Vegident.vegstatus
      RENAME_SET_VALUE nummer > vegident.Vegident.vegnummer
      RENAME_SET_VALUE hp > vegparsell.Vegparsell.hovedParsell
      RENAME_SET_VALUE meter > vegparsell.Vegparsell.veglenkeMeterFra
      SET_TO vegparsell.Vegparsell.veglenkeMeterTil = @Value(vegparsell.Vegparsell.veglenkeMeterFra)
      REMOVE kortform
      SET_TO vk = @Value(vegident.Vegident.vegkategori)
    -> ListBuilder
AnnenVegkategori: Inspector
    TACKATTRS = kategori
IngenPosisjon: Inspector
