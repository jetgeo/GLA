FME workspace 20170109_GML2API (backup).fmw

Parameters:
- SourceDataset_GML = C:\DATA\NIFS\Data\0520_Stikkrenner\Original\2016\*.gml   # Source Geography Markup Language (GML) File(s)
- SourceDataset_GML_2 = C:\DATA\NIFS\Data\NVDB\kommune\520\79\StikkrenneKulvert.gml   # Source Geography Markup Language (GML) File(s)
- DestDataset_GML_3 = C:\DATA\NIFS\Data\0520_Stikkrenner\Transformert\2016   # Destination Geography Markup Language (GML) File
- DestDataset_TEXTLINE_3 = C:\DATA\NIFS\Data\0520_Stikkrenner\XML\2016   # Destination Text File
- DestDataset_XLSXW = C:\DATA\NIFS\Data\0520_Stikkrenner\XML\2016.xlsx   # Destination Microsoft Excel File
- DakatVersjon = 2.07   # Datakatalogversjon
- Geometriegenskap = 5899

Readers:
- GML_1: GML from $(SourceDataset_GML)
- GML_2: GML from $(SourceDataset_GML_2)

Writers:
- GML_3: GML to $(DestDataset_GML_3)
- TEXTLINE_1: TEXTLINE to $(DestDataset_TEXTLINE_3)
- XLSXW_1: XLSXW to $(DestDataset_XLSXW)

Note: Originalfiler (GML)
Stikkrenne (reader GML_1)
    attributes: breddeInnvendig xml_char(255), bruksområde xml_char(255), datafangstdato xml_char(11), eier xml_char(255), endringsflagg.Endringsflagg.tidspunktEndring xml_char(11), endringsflagg.Endringsflagg.typeEndring xml_char(2), gjennomløpForElvBekk xml_char(4), harInnløpsrist xml_char(4), høydeInnvendig xml_char(255), høydereferanse xml_char(4), kvalitet.Posisjonskvalitet.målemetode xml_decimal(3,0), kvalitet.Posisjonskvalitet.målemetodeHøyde xml_decimal(3,0), kvalitet.Posisjonskvalitet.nøyaktighet xml_decimal(3,0), kvalitet.Posisjonskvalitet.nøyaktighetHøyde xml_decimal(3,0), kvalitet.Posisjonskvalitet.synbarhet xml_decimal(2,0), materialtype xml_char(255), spesielleProblem xml_char(255), tilknyttetLukkaDren xml_char(4), tilstandSkade.TilstandSkadePunkt.datoKontrollert xml_char(11), tilstandSkade.TilstandSkadePunkt.tilstand xml_char(255), tilstandSkade.TilstandSkadePunkt.tiltak xml_char(255), tverrsnittsform xml_char(255), typeInnløp xml_char(255), typeUtløp xml_char(19), vegident.Vegident.vegkategori xml_char(2), kvalitet.Posisjonskvalitet.maksimaltAvvik xml_decimal(3,0), kommentar.NVDB_Kommentar.beskrivelse xml_char(255), tilstandSkade.TilstandSkadePunkt.tilleggsinformasjon xml_char(255), byggeår xml_decimal(5,0), xml_geom_error xml_char(4),
      tilstandSkade.TilstandSkadePunkt.skadetype xml_char(255), vegident.Vegident.vegstatus xml_char(2), dokumentasjon.NVDB_Dokumentasjon.tekst xml_char(255), dokumentasjon.NVDB_Dokumentasjon.merknad xml_char(255)
    -> AttributeManager_4
AssosierteObjekter: Inspector
Note: Kobler til assosierte
FeatureMerger_4
    JOIN_KEYS = @Value(gml_id) @Value(gml_id) AUTO
    CONNECT_Z_MODE = First Wins
    SUPPLIERS_FIRST = No
    IGNORE_NULLS = Yes
    PROCESS_DUPS = Yes
    GEOM_TYPE = Build Polygons
    LIST_NAME = assosiasjoner
    MERGE_TYPE = Attributes Only
    SUPPLIER_PREFIX = assosiasjoner.
    ATTR_ACCUM_MODE = Prefix Supplier
    MERGED -> ListElementCounter
    NOT_MERGED -> ListElementCounter
ListElementCounter
    LIST_NAME = assosiasjoner{}
    CNT_ATTR = assosiasjoner.antall
    -> Counter_3
    -> Aggregator_2
Aggregator_2
    COUNT_ATTR = antall
    ORDERED = No
    SUM = assosiasjoner.antall
    AGGREGATE_TYPE = Homogeneous Collection (If Possible)
    SEP = ,
    GROUP_BY = endringsflagg.Endringsflagg.typeEndring fme_basename
    ACCUM_ATTRS_NAME = Get Attributes From One Representative Feature
    MODE = Geometry - Assemble One Level
    AGGREGATE -> AttributeManager_8
AttributeManager_8
    ATTR_TABLE:
      RENAME_SET_VALUE endringsflagg.Endringsflagg.typeEndring > typeEndring
      RENAME_SET_VALUE fme_basename > filnavn
      RENAME_SET_VALUE assosiasjoner.antall > assosierte
    -> Filer (writer XLSXW_1)
Filer (writer XLSXW_1)
    attributes: filnavn auto(20), typeEndring auto(20), antall auto(20), assosierte auto(20)
Counter_3
    START = 1
    CNT_ATTR = tempId
    DOMAIN = counter
    SCOPE = Global
    -> Counter_3_OUTPUT_-__NullAttributeMapper
Counter_3_OUTPUT_-__NullAttributeMapper: Junction
    -> NullAttributeMapper
NullAttributeMapper
    OTHER_VALUE = 0
    NULL_TREATMENT = Missing
    ATTRCHOICE = All Attributes
    SOURCE_ATTR_VAL = Null Empty "Missing (Selected Attributes Only)"
    -> AttributeExploder
    -> FeatureMerger_5 [REQUESTOR]
Note: Kobler liste med egenskaper til objektet
FeatureMerger_5
    JOIN_KEYS = @Value(tempId) @Value(tempId) AUTO
    SUPPLIERS_FIRST = No
    IGNORE_NULLS = No
    PROCESS_DUPS = No
    MERGE_TYPE = Attributes Only
    ATTR_CONFLICT_RES = Use Requestor
    ATTR_ACCUM_MODE = Merge Supplier
    MERGED -> AttributeManager_12
Note: Tilpasninger på vegObjektnivå
AttributeManager_12
    ATTR_TABLE:
      SET_TO vegObjekt.typeId = @Value(fme_feature_type)
      SET_TO vegObjekt.tempId = FME_CONDITIONAL:DEFAULT_VALUE'_FME_NO_OP_'BOOL_OP;OR;COMPOSITE_TEST;<Unused>;TEST @Value(endringsflagg.Endringsflagg.typeEndring) = N'@Value(tempId)'FME_NUM_CONDITIONS2___
      SET_TO vegObjekt.nvdbId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
      SET_TO vegObjekt.versjon = FME_CONDITIONAL:DEFAULT_VALUE'_FME_NO_OP_'BOOL_OP;OR;COMPOSITE_TEST;<Unused>;TEST @Value(endringsflagg.Endringsflagg.typeEndring) = E'@Value(identifikasjon.Identifikasjon.versjonId)'FME_NUM_CONDITIONS2___
    -> vegObjektXML [ROOT]
vegObjektXML: XMLTemplater
    ROOT_QUERY_EXPR:
      {if( fme:has-attribute("vegObjekt.nvdbId")) then
          <vegObjekt typeId="{fme:get-attribute("vegObjekt.typeId")}" nvdbId="{fme:get-attribute("vegObjekt.nvdbId")}" versjon="{fme:get-attribute("vegObjekt.versjon")}">
              <egenskaper>
              {fme:get-list-attribute("egenskaper{}.egenskap.XML")}
              {if( fme:has-attribute("_geometry")) then
              <egenskap typeId="$(Geometriegenskap)" operasjon="oppdater">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjon.XML")}
              </assosiasjoner>
              else ()}
              <lokasjon operasjon="oppdater">
                  <punkt lenkeId="{fme:get-attribute("ReflinkOID")}" posisjon="{fme:get-attribute("Measure")}" />
              </lokasjon>
          </vegObjekt>
      else
          <vegObjekt typeId="{fme:get-attribute("vegObjekt.typeId")}" tempId="-{fme:get-attribute("tempId")}">
              <egenskaper>
              {fme:get-list-attribute("egenskaper{}.egenskap.XML")}
              {if( fme:has-attribute("_geometry")) then
              <egenskap typeId="$(Geometriegenskap)">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjon.XML")}
              </assosiasjoner>
              else ()}
              <lokasjon>
                  <punkt lenkeId="{fme:get-attribute("ReflinkOID")}" posisjon="{fme:get-attribute("Measure")}" />
              </lokasjon>
          </vegObjekt>}
    VISIBLE_QUERY_VALIDATE = Yes
    RESULT_ATTRIBUTE = vegObjekt.XML
    OUTPUT_XML_HEADER = No
    -> StringReplacer_3
ListBuilder_3
    LIST_NAME = vegObjektliste
    GRP_BY = endringsflagg.Endringsflagg.typeEndring fme_basename
    -> EndringssettXML [ROOT]
EndringssettXML: XMLTemplater
    ROOT_QUERY_EXPR:
        {if( {fme:get-attribute("endringsflagg.Endringsflagg.typeEndring")}="E") then
        <delvisOppdater>
          <vegObjekter>
          {fme:get-list-attribute("vegObjektliste{}.vegObjekt.XML")}
          </vegObjekter>
        </delvisOppdater>
        else if( {fme:get-attribute("endringsflagg.Endringsflagg.typeEndring")}="N") then
        <registrer>
          <vegObjekter>
          {fme:get-list-attribute("vegObjektliste{}.vegObjekt.XML")}
          </vegObjekter>
        </registrer>
        else ()}
    VISIBLE_QUERY_VALIDATE = Yes
    RESULT_ATTRIBUTE = endringssett.XML
    OUTPUT_XML_HEADER = No
    -> AttributeKeeper_7
ListBuilder_4
    LIST_NAME = endringsliste
    GRP_BY = fme_basename
    -> TimeStamper
TimeStamper
    FMT = ^Y-^m-^d
    TIME_ATTR = _timestamp
    -> EndringslisteXML [ROOT]
EndringslisteXML: XMLTemplater
    ROOT_QUERY_EXPR:
      <endringssett xmlns="http://nvdb.vegvesen.no/apiskriv/domain/v2" effektDato="{fme:get-attribute("_timestamp")}" datakatalogversjon="$(DakatVersjon)">
      {fme:get-list-attribute("endringsliste{}.endringssett.XML")}
      </endringssett>
    VISIBLE_QUERY_VALIDATE = Yes
    RESULT_ATTRIBUTE = endringsliste.XML
    OUTPUT_XML_HEADER = No
    -> StringReplacer
Sampler
    SAMPLE_MODE = No
    GROUP_BY = fme_feature_type fme_basename
    RATE = 1
    SAMPLE_TYPE_LONG = Every Nth Feature
    SAMPLED -> AttributeRenamer_4
AttributeRenamer_4
    ATTR_TABLE = RENAME_SET_DEFAULT _xml_output > text_line_data
    -> text_line (writer TEXTLINE_1)
Note: En xml-fil pr GML-fil
text_line (writer TEXTLINE_1)
    attributes: text_line_data buffer
vegObjekt: Inspector
    TACKATTRS = assosiasjoner.antall endringsflagg.Endringsflagg.typeEndring vegObjekt.typeId
AttributeRemover_3
    REMOVE_ATTRS = gml_id
    -> Stikkrenne (writer GML_3)
Note: Eksporterer til korrigerte GML-filer
Stikkrenne (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer, bruksområde xml_buffer,
      senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer

Bookmark: Vasking av originalfiler
Note: AttributeManager_4 [AttributeManager:1] / Substitute Missing, Null and Empty by: No Substitution / Rename 'dokumentasjon.NVDB_Dokumentasjon.tekst' to 'kommentar.NVDB_Kommentar.beskrivelse' / Rename 'dokumentasjon.NVDB_Dokumentasjon.merknad' to 'kommentar.NVDB_Kommentar.beskrivelse' / Set 'endringsflagg.Endringsflagg.typeEndring' to ' / If ("endringsflagg.Endringsflagg.typeEndring" ATTRIBUTE_IS_MISSING "") Then "N" / Else "<Do Nothing>" / ' / Set 'endringsflagg.Endringsflagg.tidspunktEndring' to ' / If ("endringsflagg.Endringsflagg.tidspunktEndring" ATTRIBUTE_IS_MISSING "") AND ("@Value(datafangstdato)" ATTRIBUTE_HAS_VALUE "") Then / "@Value(datafangstdato)" / Else If ("endringsflagg.Endringsflagg.tidspunktEndring" ATTRIBUTE_IS_MISSING "") Then "2016-12-31" / Else "<Do Nothing>" / ' / Set 'vk' to '@Value(vegident.Vegident.vegkategori)' / Version: 1 / Last Parameter Edit: Build 16481
AttributeManager_4
    ATTR_TABLE:
      RENAME_SET_VALUE dokumentasjon.NVDB_Dokumentasjon.tekst > kommentar.NVDB_Kommentar.beskrivelse
      RENAME_SET_VALUE dokumentasjon.NVDB_Dokumentasjon.merknad > kommentar.NVDB_Kommentar.beskrivelse
      SET_TO endringsflagg.Endringsflagg.typeEndring = FME_CONDITIONAL:DEFAULT_VALUE'_FME_NO_OP_'BOOL_OP;OR;COMPOSITE_TEST;<Unused>;TEST endringsflagg.Endringsflagg.typeEndring ATTRIBUTE_IS_MISSING _FME_BLANK_STRING_'N'FME_NUM_CONDITIONS2___
      SET_TO endringsflagg.Endringsflagg.tidspunktEndring = FME_CONDITIONAL:DEFAULT_VALUE'_FME_NO_OP_'BOOL_OP;AND;COMPOSITE_TEST;<Unused>;TEST endringsflagg.Endringsflagg.tidspunktEndring ATTRIBUTE_IS_MISSING _FME_BLANK_STRING_;TEST @Value(datafangstdato) ATTRIBUTE_HAS_VALUE _FME_BLANK_STRING_'@Value(datafangstdato)'BOOL_OP;AND;COMPOSITE_TEST;<Unused>;TEST endringsflagg.Endringsflagg.tidspunktEndring ATTRIBUTE_IS_MISSING _FME_BLANK_STRING_'2016-12-31'FME_NUM_CONDITIONS3___
      SET_TO vk = @Value(vegident.Vegident.vegkategori)
    -> Reprojector
Reprojector
    RASTER_CELL_SIZE = Preserve Cells
    DEST = EPSG:25833
    SOURCE = Read from feature
    INTERPOLATION_TYPE_NAME = Nearest Neighbor
    REPROJECTED -> CenterPointExtractor

Bookmark: Finner posisjon i vegnettet
CenterPointExtractor
    CENTY = _y
    MODE = Center
    CENTX = _x
    CENTZ = _z
    -> AttributeCreator_2
AttributeCreator_2
    ATTR_TABLE = SET_TO httpReq = https://www.vegvesen.no/nvdb/api/v2/posisjon.xml?nord=@Value(_y)&ost=@Value(_x)&vegreferanse=@Value(vegident.Vegident.vegkategori)
    -> HTTPCaller_2
Note: Finner vegreferanse for representasjonspunktet, med filter på vegkategori
HTTPCaller_2
    FOLLOW_REDIRECTS = Yes
    CONNECTION_TIMEOUT_LENGTH = 60
    USE_COOKIES = No
    TARGET_ATTR_ENCODING = auto-detect
    FILE_TYPE = <Auto Detect from HTTP Headers>
    STATUS_CODE_ATTR = _http_status_code
    HTTP_METHOD = GET
    TARGET_ATTR = _response_body
    VERIFY_SSL_CERTIFICATES = Yes
    SAVE_FILE = Attribute
    RESPONSE_HEADER_LIST_ATTR = _headers
    TARGET_URL = @Value(httpReq)
    TRANSFER_TIMEOUT_LENGTH = 90
    ERROR_ATTR = _error
    -> XMLFlattener_2
    <Rejected> -> AttributeCreator_3
XMLFlattener_2
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = id posisjon
    ATTRIBUTE_XML = _response_body
    FEATURE_TYPES_FORMAT_NAME = XML
    EMBEDDED_EXPRESSIONS = veglenke
    XML_SOURCE_TYPE = Attribute with XML document
    -> TestFilter
Note: Ekstra kontroll på at objektene har fått posisjon. Får en del tilfeller der det ikke gis feil, men bare tomt svar
TestFilter
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_5
    <UNFILTERED> -> AttributeCreator_3
XMLFlattener_5
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = fylke kommune kategori status nummer hp meter kortform
    ATTRIBUTE_XML = _response_body
    FEATURE_TYPES_FORMAT_NAME = XML
    EMBEDDED_EXPRESSIONS = vegreferanse
    XML_SOURCE_TYPE = Attribute with XML document
    -> AttributeManager
AttributeCreator_3
    ATTR_TABLE = SET_TO httpReq = https://www.vegvesen.no/nvdb/api/v2/posisjon.xml?nord=@Value(_y)&ost=@Value(_x)
    -> HTTPCaller_3
Note: Finner vegreferanse for representasjonspunktet, uten filter på vegkategori
HTTPCaller_3
    FOLLOW_REDIRECTS = Yes
    CONNECTION_TIMEOUT_LENGTH = 60
    USE_COOKIES = No
    TARGET_ATTR_ENCODING = auto-detect
    FILE_TYPE = <Auto Detect from HTTP Headers>
    STATUS_CODE_ATTR = _http_status_code
    HTTP_METHOD = GET
    TARGET_ATTR = _response_body
    VERIFY_SSL_CERTIFICATES = Yes
    SAVE_FILE = Attribute
    RESPONSE_HEADER_LIST_ATTR = _headers
    TARGET_URL = @Value(httpReq)
    TRANSFER_TIMEOUT_LENGTH = 90
    ERROR_ATTR = _error
    -> XMLFlattener_4
    <Rejected> -> IngenPosisjon
XMLFlattener_4
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = id posisjon
    ATTRIBUTE_XML = _response_body
    FEATURE_TYPES_FORMAT_NAME = XML
    EMBEDDED_EXPRESSIONS = veglenke
    XML_SOURCE_TYPE = Attribute with XML document
    -> TestFilter_2
Note: Ekstra kontroll på at objektene har fått posisjon. Får en del tilfeller der det ikke gis feil, men bare tomt svar
TestFilter_2
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_3
    <UNFILTERED> -> IngenPosisjon
XMLFlattener_3
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = fylke kommune kategori status nummer hp meter kortform
    ATTRIBUTE_XML = _response_body
    FEATURE_TYPES_FORMAT_NAME = XML
    EMBEDDED_EXPRESSIONS = vegreferanse
    XML_SOURCE_TYPE = Attribute with XML document
    -> AnnenVegkategori
    -> AttributeManager
AttributeManager
    ATTR_TABLE:
      REMOVE vegident.Vegident.vegkategori
      REMOVE httpReq
      REMOVE _x
      REMOVE _y
      REMOVE _z
      REMOVE _error
      REMOVE _headers{}.name
      REMOVE _headers{}.value
      REMOVE _response_body
      REMOVE _http_status_code
      RENAME_SET_VALUE id > ReflinkOID
      RENAME_SET_VALUE posisjon > Measure
      REMOVE fylke
      REMOVE kommune
      RENAME_SET_VALUE kategori > vegident.Vegident.vegkategori
      RENAME_SET_VALUE status > vegident.Vegident.vegstatus
      RENAME_SET_VALUE nummer > vegident.Vegident.vegnummer
      RENAME_SET_VALUE hp > vegparsell.Vegparsell.hovedParsell
      RENAME_SET_VALUE meter > vegparsell.Vegparsell.veglenkeMeterFra
      SET_TO vegparsell.Vegparsell.veglenkeMeterTil = @Value(vegparsell.Vegparsell.veglenkeMeterFra)
      REMOVE kortform
      SET_TO vk = @Value(vegident.Vegident.vegkategori)
    -> UUIDGenerator
UUIDGenerator
    UUID_ATTR = gml_id
    -> NeighborFinder [BASE]
AnnenVegkategori: Inspector
    TACKATTRS = kategori vegident.Vegident.vegkategori
IngenPosisjon: Inspector

Bookmark: Kobler til eksisterende objekter fra NVDB, og setter typeEndring=E ved treff
Note: Eksisterende objekter fra NVDB (GML)
StikkrenneKulvert (reader GML_2)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, vegreferanse{}.Vegreferanse.veglenkeMeterFra xml_int64, vegreferanse{}.Vegreferanse.veglenkeMeterTil xml_int64, vegreferanse{}.Vegreferanse.referanseretning xml_buffer, vegreferanse{}.Vegreferanse.vegreferanseFraDato xml_date, vegreferanse{}.Vegreferanse.vegreferanseTilDato xml_date, bruksområde xml_buffer, navn xml_buffer, byggeår xml_int64, produktinformasjon xml_buffer,
      materialtype xml_buffer, prefabrikkert xml_buffer, retning xml_buffer, vinkel xml_buffer, tilknyttetLukkaDren xml_buffer, gjennomløpForElvBekk xml_buffer, typeInnløp xml_buffer, typeUtløp xml_buffer, harInnløpsrist xml_buffer, diameterInnvendig xml_int64, breddeInnvendig xml_int64, høydeInnvendig xml_int64, lengde xml_real64, helningFall xml_real64, overfyllingInnløp xml_real64, overfyllingUtløp xml_real64, tykkelseOverfylling xml_real64, driftsmerking xml_buffer, tverrsnittsform xml_buffer, fundamentering xml_buffer, rehabilitering xml_buffer, posisjon xml_geometry, senterlinje xml_geometry, tilleggsinformasjon xml_buffer, varmekabler xml_buffer, antallTininger xml_int64, spesielleProblem xml_buffer, FKB_ID xml_buffer, eier xml_buffer, vedlikeholdsansvarlig xml_buffer,
      område xml_geometry, høydePassasje xml_int64, lineærPosisjon{}.LineærPosisjonPunkt.lineærReferanseMetode xml_buffer, lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer, lineærPosisjon{}.LineærPosisjonPunkt.nettverkselement.owns xml_boolean, lineærPosisjon{}.LineærPosisjonPunkt.posisjon xml_real64, assosiertKum{}.owns xml_boolean, assosiertKum{}.nilReason xml_buffer, assosiertKum{}.gml_remoteSchema xml_buffer, assosiertKum{}.xlink_href xml_buffer, assosiertSystemobjekt{}.owns xml_boolean, assosiertSystemobjekt{}.nilReason xml_buffer, assosiertSystemobjekt{}.gml_remoteSchema xml_buffer, assosiertSystemobjekt{}.xlink_href xml_buffer, assosiertTilstandsgrad_StikkrenneKulvert{}.owns xml_boolean, assosiertTilstandsgrad_StikkrenneKulvert{}.nilReason xml_buffer, assosiertTilstandsgrad_StikkrenneKulvert{}.gml_remoteSchema xml_buffer, assosiertTilstandsgrad_StikkrenneKulvert{}.xlink_href xml_buffer, assosiertKommentar{}.owns xml_boolean, assosiertKommentar{}.nilReason xml_buffer, assosiertKommentar{}.gml_remoteSchema xml_buffer, assosiertKommentar{}.xlink_href xml_buffer, assosiertTilstandSkade_Punkt{}.owns xml_boolean, assosiertTilstandSkade_Punkt{}.nilReason xml_buffer, assosiertTilstandSkade_Punkt{}.gml_remoteSchema xml_buffer, assosiertTilstandSkade_Punkt{}.xlink_href xml_buffer,
      assosiertTilstandSkadeFU_Punkt{}.owns xml_boolean, assosiertTilstandSkadeFU_Punkt{}.nilReason xml_buffer, assosiertTilstandSkadeFU_Punkt{}.gml_remoteSchema xml_buffer, assosiertTilstandSkadeFU_Punkt{}.xlink_href xml_buffer, assosiertDokumentasjon{}.owns xml_boolean, assosiertDokumentasjon{}.nilReason xml_buffer, assosiertDokumentasjon{}.gml_remoteSchema xml_buffer, assosiertDokumentasjon{}.xlink_href xml_buffer
    -> ListExploder
    -> Eksisterende_NVDB
ListExploder
    LIST_ATTR = vegreferanse{}
    ATTR_CONFLICT_RES = Use Incoming List
    INDEX_ATTR = _element_index
    ATTR_ACCUM_MODE = Merge Incoming List
    ELEMENTS -> AttributeManager_2
Note: Fjerner tilstandsegenskaper
AttributeManager_2
    ATTR_TABLE:
      REMOVE gml_id
      REMOVE rehabilitering
      REMOVE antallTininger
      REMOVE spesielleProblem
      SET_TO vk = @Value(Vegreferanse.vegkategori)
      SET_TO NVDB_ID = @Value(identifikasjon.Identifikasjon.lokalId)
    -> NeighborFinder [CANDIDATE]
Note: Kobling til eksisterende i NVDB
NeighborFinder
    MAX = 10
    INSERT_VERTEX = No
    CANDIDATES_FIRST = No
    TREAT_POLYGON_AS = Lines
    ATTR_CONFLICT_RES = Use Base
    GROUP_BY = vk
    K = 3
    MODE = Bases and Candidates
    CLOSE_LIST_NAME = _ccList
    ATTR_ACCUM_MODE = Merge Candidate
    MATCHED -> NeighborFinder_MATCHED
    MATCHED -> AttributeKeeper
    UNMATCHED_BASE -> NeighborFinder_MATCHED
AttributeKeeper
    KEEP_LIST = _ccList{}
    KEEP_ATTRS = gml_id
    -> GeometryExtractor
GeometryExtractor
    KIND_LONG = FME Binary
    REMOVE_GEOMETRY = No
    ATTR = _geometry
    -> ListDuplicateRemover
ListDuplicateRemover
    SRC_LIST = _ccList{}.NVDB_ID
    -> ListExploder_2
ListExploder_2
    LIST_ATTR = _ccList{}
    ATTR_CONFLICT_RES = Use Original
    INDEX_ATTR = _element_index
    ATTR_ACCUM_MODE = Merge Incoming List
    ELEMENTS -> ListBuilder
Note: Liste pr eksisterende objekt
ListBuilder
    LIST_NAME = _list
    GRP_BY = NVDB_ID
    -> ListSorter
ListSorter
    SRC_LIST = _list{}.distance
    TYPE = Alphabetic
    ORDER = Ascending
    -> ListIndexer
Note: Henter ut nærmeste nye pr NVDB-ID
ListIndexer
    LIST_ATTR = _list{}
    INDEX = 0
    -> GeometryReplacer
GeometryReplacer
    SOURCE = @Value(_geometry)
    REMOVE_ATTRIBUTE = Yes
    KIND_LONG = FME Binary
    -> AttributeRemover
AttributeRemover
    REMOVE_ATTRS = spesielleProblem
    LIST_ATTRS = _list{}
    -> AttributeRemover_OUTPUT
Note: FeatureMerger : Supplier
AttributeRemover_OUTPUT: Junction
    -> FeatureMerger_SUPPLIER
Note: AttributeRemover : Output
FeatureMerger_SUPPLIER: Junction
    -> FeatureMerger [SUPPLIER]
NeighborFinder_MATCHED: Junction
    -> AttributeRemover_2
AttributeRemover_2
    REMOVE_ATTRS = _closest_candidate_x,_closest_candidate_y,_distance,_closest_base_x,_candidate_angle,retning,_angle,_candidate_label_angle,identifikasjon.Identifikasjon.versjonId,_closest_base_y,identifikasjon.Identifikasjon.lokalId,identifikasjon.Identifikasjon.navnerom,sideposisjon,NVDB_ID
    LIST_ATTRS = _ccList{}
    -> FeatureMerger [REQUESTOR]
Note: Kobler gammel og nytt objekt. Attributter fra nytt objekt vinner, men dersom de mangler brukes attributter fra gammelt objekt
FeatureMerger
    JOIN_KEYS = @Value(gml_id) @Value(gml_id) AUTO
    SUPPLIERS_FIRST = No
    IGNORE_NULLS = No
    REJECT_NULL_MISSING_KEYS = No
    PROCESS_DUPS = No
    MERGE_TYPE = Attributes Only
    ATTR_CONFLICT_RES = Use Requestor
    ATTR_ACCUM_MODE = Merge Supplier
    MERGED -> AttributeManager_3
    NOT_MERGED -> FeatureMerger_NOT_MERGED_-__AttributeRemover_3
Note: Setter vegkategori fra eksisterende, og angir typeEndring=E
AttributeManager_3
    ATTR_TABLE:
      SET_TO endringsflagg.Endringsflagg.typeEndring = E
      REMOVE vegident.Vegident.vegkategori
      RENAME_SET_VALUE Vegreferanse.vegkategori > vegident.Vegident.vegkategori
    -> FeatureMerger_NOT_MERGED_-__AttributeRemover_3
    -> AttributeKeeper_3
FeatureMerger_NOT_MERGED_-__AttributeRemover_3: Junction
    -> AttributeRemover_3
    -> SchemaMapper
Eksisterende_NVDB: Inspector

Bookmark: Identifiserer assosierte tilstandskadeobjekter og systemobjekter, og setter til sletting
AttributeKeeper_3
    KEEP_LIST = assosiertDokumentasjon{} assosiertKommentar{} assosiertKum{} assosiertSystemobjekt{} assosiertTilstandSkadeFU_Punkt{} assosiertTilstandSkade_Punkt{} assosiertTilstandsgrad_StikkrenneKulvert{}
    -> ListExploder_6
    -> ListExploder_8
    -> ListExploder_9
Note: Fjerne systemobjekter og tilstandskade-objekter fra eksisterende
ListExploder_6
    LIST_ATTR = assosiertSystemobjekt{}
    ATTR_CONFLICT_RES = Use Incoming List
    INDEX_ATTR = _element_index
    ATTR_ACCUM_MODE = Merge Incoming List
    ELEMENTS -> AttributeKeeper_2
ListExploder_8
    LIST_ATTR = assosiertTilstandSkade_Punkt{}
    ATTR_CONFLICT_RES = Use Incoming List
    INDEX_ATTR = _element_index
    ATTR_ACCUM_MODE = Merge Incoming List
    ELEMENTS -> AttributeKeeper_2
ListExploder_9
    LIST_ATTR = assosiertTilstandSkadeFU_Punkt{}
    ATTR_CONFLICT_RES = Use Incoming List
    INDEX_ATTR = _element_index
    ATTR_ACCUM_MODE = Merge Incoming List
    ELEMENTS -> AttributeKeeper_2
AttributeKeeper_2
    KEEP_ATTRS = xlink_href
    -> AttributeSplitter
AttributeSplitter
    TRIM_OPTION = Both
    LIST_NAME = _list
    ATTR_NAME = xlink_href
    DROP_EMPTY_PARTS = No
    DELIMITER = #
    -> ListIndexer_2
ListIndexer_2
    LIST_ATTR = _list{}
    INDEX = 0
    -> AttributeManager_5
AttributeManager_5
    ATTR_TABLE = RENAME_SET_VALUE _list > _file
    -> ListIndexer_3
    -> Aggregator
Aggregator
    ORDERED = No
    AGGREGATE_TYPE = Homogeneous Collection (If Possible)
    SEP = ,
    GROUP_BY = _file
    ACCUM_ATTRS_NAME = Get Attributes From One Representative Feature
    MODE = Geometry - Assemble One Level
    AGGREGATE -> FeatureReader [INITIATOR]
Note: Leser alle assosierte objekter
FeatureReader
    ATTR_ACCUM_MODE = Only Use Result
    FORMAT = GML
    GML_CLIP_TO_ENVELOPE = NO
    GML_MAP_GEOMETRY_COLUMNS = YES
    GML_FLATTEN_XML_FRAGMENTS = NO
    GML_MULTI_VALUE_SIMPLE_PROPERTIES_AS_CSV = no
    GML_DISABLE_AUTOMATIC_READER_TYPE_SELECTION = NO
    GML_CONTINUE_ON_GEOM_ERROR = yes
    GML_CACHE_XSD = yes
    GML_IGNORE_APPLICATON_SCHEMA = yes
    GML_MAP_PREDEFINED_GML_PROPERTIES = NO
    GML_ADD_GEOMETRIES_AS_XML_FRAGMENTS = NO
    GML_USE_OLD_READER = NO
    GML_MAP_ALL_SUBSTITUTABLE_PROPERTIES = YES
    COMBINE_GEOM = Use Result
    OUTPUT_FEATURES_DISPLAY = Schema and Data Features
    GML_USE_SEARCH_ENVELOPE = NO
    INTERACT = <No Spatial Filter>
    GML_MAP_COMPLEX_PROPERTIES_AS = Nested Attributes
    DATASET = C:\DATA\NIFS\Data\NVDB\kommune\520\79\@Value(_file)
    GML_ENFORCE_PATH_CONTINUITY_BY = SNAPPING_END_POINTS
    GML_SKIP_SCHEMA_LOCATION_IN_DATASET = No
    GML_FEATURE_TYPES_SCHEMA_MODE = XML_SCHEMA
    GML_VALIDATE_DATASET = no
    GML_MAP_EMBEDDED_OBJECTS_AS = ATTRIBUTES
    GML_DISABLE_XML_NAMESPACE_PROCESSING = NO
    GML_XML_FRAGMENTS_AS_DOCUMENTS = YES
    <OTHER> -> FeatureReader__Generic_
    <OTHER> -> AttributeExposer_2
FeatureReader__Generic_: Inspector
AttributeExposer_2
    ATTR_LIST = gml_id
    -> FeatureMerger_2 [REQUESTOR]
ListIndexer_3
    LIST_ATTR = _list{}
    INDEX = 1
    -> AttributeManager_6
AttributeManager_6
    ATTR_TABLE:
      REMOVE _list{}
      RENAME_SET_VALUE _list > _object
    -> FeatureMerger_2 [SUPPLIER]
FeatureMerger_2
    JOIN_KEYS = @Value(gml_id) @Value(_object) AUTO
    SUPPLIERS_FIRST = No
    IGNORE_NULLS = No
    REJECT_NULL_MISSING_KEYS = No
    PROCESS_DUPS = No
    MERGE_TYPE = Attributes Only
    ATTR_CONFLICT_RES = Use Requestor
    ATTR_ACCUM_MODE = Merge Supplier
    MERGED -> AttributeManager_7
Note: Setter assosierte objekter til sletting (endrinsType=S)
AttributeManager_7
    ATTR_TABLE = SET_TO endringsflagg.Endringsflagg.typeEndring = S
    -> AssosierteObjekter
    -> FeatureMerger_4 [SUPPLIER]

Bookmark: Mapping til Datakatalog-IDer
Note: Mapper objekttypenavn til VOT-ID vha mappingtabell ftMapping
SchemaMapper
    CSV__STRIP_QUOTES = yes
    CSV__ALLOW_SPACES_IN_COLUMN_NAMES = yes
    ROW_ID_ATTR = _schemamapper_row_ids
    TABLE = CSV
    IDXSOURCEATTR = fme_feature_type
    CSV__SKIP_LINES = 1
    CSV__IN_FIELD_NAMES = YES
    CSV__SCHEMA = number,3,0,char,18,
    IDXSOURCECOL = name
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    FORMAT = CSV
    IDXDESTCOL = ftid
    DATASET = C:\DATA\NIFS\Mapping\NIFS_ftMapping.csv
    IDXDESTATTR = fme_feature_type
    CSV__IN_SEPARATOR = ;
    CSV__SKIP_FOOTER = 0
    CSV__FIELD_NAMES_AFTER_HEADER = no
    CSV__DUPLICATE_DELIMS = no
    CSV__SCHEMA_WITH_COL_NAMES = ftid,number,3,0,name,char,18,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__GROUP_BY_DATASET = no
    CSV_SCAN_MAX_FEATURES = 1000
    MAPPED -> AttributeExposer
AttributeExposer
    ATTR_LIST = fme_feature_type
    -> SchemaMapper_2
Note: Mapper egenskapsnavn til ET-ID vha mappingtabell ptMapping
SchemaMapper_2
    CSV__STRIP_QUOTES = yes
    CSV__ALLOW_SPACES_IN_COLUMN_NAMES = yes
    ROW_ID_ATTR = _schemamapper_row_ids
    TABLE = CSV
    IDXSOURCEATTR = fme_feature_type
    CSV__SKIP_LINES = 1
    CSV__IN_FIELD_NAMES = YES
    CSV__SCHEMA = char,17,,number,4,0,number,6,0,char,43,
    IDXSOURCECOL = ""
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    FORMAT = CSV
    MAP_ATTRS = name ptid $(FME_ASC_16)
    IDXDESTCOL = ""
    DATASET = C:\DATA\NIFS\Mapping\NIFS_ptMapping.csv
    IDXDESTATTR = fme_feature_type
    CSV__IN_SEPARATOR = ;
    MATCH_ATTRS = ft_attr ftid
    CSV__SKIP_FOOTER = 0
    CSV__FIELD_NAMES_AFTER_HEADER = no
    CSV__DUPLICATE_DELIMS = no
    CSV__SCHEMA_WITH_COL_NAMES = ft_attr,char,17,,ftid,number,4,0,ptid,number,6,0,name,char,43,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__GROUP_BY_DATASET = no
    CSV_SCAN_MAX_FEATURES = 1000
    MAPPED -> AttributeExposer_3
    MAPPED -> AttributeExposer_4

Bookmark: Lager geometristreng
AttributeExposer_4
    ATTR_LIST = 1832
    -> AttributeManager_13
AttributeManager_13
    ATTR_TABLE = SET_TO 1832 = FME_CONDITIONAL:DEFAULT_VALUE'FME_NULL_VALUE'BOOL_OP;OR;COMPOSITE_TEST;<Unused>;TEST @Value(1832) = nei;TEST @Value(1832) = Nei'Nei'BOOL_OP;OR;COMPOSITE_TEST;<Unused>;TEST @Value(1832) = ja;TEST @Value(1832) = Ja'Ja'FME_NUM_CONDITIONS3___
    -> CoordinateRounder
CoordinateRounder
    XPREC = 3
    YPREC = 3
    ZPREC = 3
    ROUNDED -> CoordinateConcatenator
CoordinateConcatenator
    COORDINATES_TO_INCLUDE_DIS = X Y Z
    PRECISION = No
    COORD_ATTR = _coordinates
    ELEMENT_DELIM = " "
    COORD_DELIM = ,
    -> StringConcatenator
StringConcatenator
    PARM_LINE = LINESTRING(@Value(_coordinates))
    VAL_ATTR = _geometry
    ACTION = Create New Attribute
    -> PythonCaller
Note: Kvalitetsstreng
PythonCaller
    NEW_ATTRIBUTES = qualityString
    PYTHONSYMBOL = setQuality
    PYTHONSOURCE:
      import fmeobjects
      # Template Function interface:

      def setQuality(feature):
          qs=""
          qm = feature.getAttribute('kvalitet.Posisjonskvalitet.målemetode')
          qms=str(qm)
          if qms <> "None":
              qs="målemetode="+qms

          qm = feature.getAttribute('kvalitet.Posisjonskvalitet.nøyaktighet')
          qms=str(qm)
          if qms <> "None":
              qs=qs+"; nøyaktighet="+qms

          qm = feature.getAttribute('kvalitet.Posisjonskvalitet.synbarhet')
          qms=str(qm)
          if qms <> "None":
              qs=qs+"; synbarhet="+qms

          qm = feature.getAttribute('kvalitet.Posisjonskvalitet.målemetodeHøyde')
          qms=str(qm)
          if qms <> "None":
              qs=qs+"; målemetodeHøyde="+qms

          qm = feature.getAttribute('kvalitet.Posisjonskvalitet.nøyaktighetHøyde')
          qms=str(qm)
          if qms <> "None":
              qs=qs+"; nøyaktighetHøyde="+qms

          if qs <> "":
              feature.setAttribute('qualityString', qs+'; ')
    -> FeatureMerger_4 [REQUESTOR]

Bookmark: Spesialhåndtering av assosiert tilstand/skade og kommentar for disse dataene, ikke permanent løsning
AttributeExposer_3
    ATTR_LIST = tilstandSkade.TilstandSkadePunkt.tiltakNår,tilstandSkade.TilstandSkadePunkt.datoKontrollert,tilstandSkade.TilstandSkadePunkt.skadetype,tilstandSkade.TilstandSkadePunkt.tilleggsinformasjon,tilstandSkade.TilstandSkadePunkt.tilstand,tilstandSkade.TilstandSkadePunkt.tiltak,kommentar.NVDB_Kommentar.beskrivelse
    -> TestFilter_3
    -> TestFilter_4
TestFilter_3
    TEST_LIST:
      BOOL_OP,OR,COMPOSITE_TEST,<Unused>,TEST_CLAUSE,"TEST @Value(tilstandSkade.TilstandSkadePunkt.datoKontrollert) ATTRIBUTE_HAS_VALUE """"
      TEST @Value(tilstandSkade.TilstandSkadePunkt.skadetype) ATTRIBUTE_HAS_VALUE """"
      TEST @Value(tilstandSkade.TilstandSkadePunkt.tilleggsinformasjon) ATTRIBUTE_HAS_VALUE """"
      TEST @Value(tilstandSkade.TilstandSkadePunkt.tilstand) ATTRIBUTE_HAS_VALUE """"
      TEST @Value(tilstandSkade.TilstandSkadePunkt.tiltak) ATTRIBUTE_HAS_VALUE """"
      TEST @Value(tilstandSkade.TilstandSkadePunkt.tiltakNår) ATTRIBUTE_HAS_VALUE """"",TilstandSkade
    DEFAULT_VALUE = <UNFILTERED>
    TilstandSkade -> AttributeManager_10
AttributeManager_10
    ATTR_TABLE:
      REMOVE endringsflagg.Endringsflagg.tidspunktEndring
      RENAME_SET_VALUE tilstandSkade.TilstandSkadePunkt.tilstand > 7596
      RENAME_SET_VALUE tilstandSkade.TilstandSkadePunkt.skadetype > 7590
      RENAME_SET_VALUE tilstandSkade.TilstandSkadePunkt.datoKontrollert > 8777
      RENAME_SET_VALUE tilstandSkade.TilstandSkadePunkt.tiltak > 7594
      RENAME_SET_VALUE tilstandSkade.TilstandSkadePunkt.tiltakNår > 7595
      RENAME_SET_VALUE tilstandSkade.TilstandSkadePunkt.tilleggsinformasjon > 7859
      SET_TO fme_feature_type = 761
      SET_TO assosiasjon.typeId = 221093
      SET_TO assosiasjon.operasjon = FME_CONDITIONAL:DEFAULT_VALUE'_FME_NO_OP_'BOOL_OP;OR;COMPOSITE_TEST;<Unused>;TEST @Value(endringsflagg.Endringsflagg.typeEndring) = E'oppdater'FME_NUM_CONDITIONS2___
      SET_TO endringsflagg.Endringsflagg.typeEndring = N
    -> AttributeKeeper_6
TestFilter_4
    TEST_LIST = BOOL_OP,OR,COMPOSITE_TEST,<Unused>,TEST_CLAUSE,"TEST @Value(kommentar.NVDB_Kommentar.beskrivelse) ATTRIBUTE_HAS_VALUE """"",Kommentar
    DEFAULT_VALUE = <UNFILTERED>
    Kommentar -> AttributeManager_11
AttributeManager_11
    ATTR_TABLE:
      SET_TO fme_feature_type = 297
      SET_TO assosiasjon.typeId = 220384
      SET_TO assosiasjon.operasjon = FME_CONDITIONAL:DEFAULT_VALUE'_FME_NO_OP_'BOOL_OP;OR;COMPOSITE_TEST;<Unused>;TEST @Value(endringsflagg.Endringsflagg.typeEndring) = E'oppdater'FME_NUM_CONDITIONS2___
      SET_TO endringsflagg.Endringsflagg.typeEndring = N
      RENAME_SET_VALUE kommentar.NVDB_Kommentar.beskrivelse > 1086
    -> AttributeKeeper_6
AttributeKeeper_6
    KEEP_ATTRS = 7595,7596,gml_id,7594,Measure,endringsflagg.Endringsflagg.tidspunktEndring,7859,endringsflagg.Endringsflagg.typeEndring,ReflinkOID,assosiasjon.typeId,fme_basename,7590,8777,1086,assosiasjon.operasjon,fme_feature_type,sideposisjon
    -> Counter_2
Counter_2
    START = 1
    CNT_ATTR = tempId
    DOMAIN = counter
    SCOPE = Global
    -> assosiasjonXML [ROOT]
assosiasjonXML: XMLTemplater
    ROOT_QUERY_EXPR:
      {if( fme:has-attribute("assosiasjon.operasjon")) then
      <assosiasjon typeId="{fme:get-attribute("assosiasjon.typeId")}" operasjon="{fme:get-attribute("assosiasjon.operasjon")}"><tempId>-{fme:get-attribute("tempId")}</tempId></assosiasjon>
      else
      <assosiasjon typeId="{fme:get-attribute("assosiasjon.typeId")}"><tempId>-{fme:get-attribute("tempId")}</tempId></assosiasjon>}
    VISIBLE_QUERY_VALIDATE = Yes
    RESULT_ATTRIBUTE = assosiasjon.XML
    OUTPUT_XML_HEADER = No
    -> GeometryRemover
GeometryRemover
    -> Counter_3_OUTPUT_-__NullAttributeMapper
    -> AttributeKeeper_4
AttributeKeeper_4
    KEEP_ATTRS = tempId,gml_id,assosiasjon.XML,assosiasjon.typeId,fme_basename,operasjon,assosiasjon.operasjon,fme_feature_type
    -> FeatureMerger_4 [SUPPLIER]

Bookmark: Liste med egenskaper
AttributeExploder
    ATTR_NAME_LABEL = _attr_name
    KEEP_ATTRIBUTES = Yes
    ATTR_VALUE_LABEL = _attr_value
    EXPLODING_TYPE = Features
    KEEP_GEOMETRY = No
    -> AttributeKeeper_5
AttributeKeeper_5
    KEEP_ATTRS = endringsflagg.Endringsflagg.typeEndring,_attr_value,tempId,_attr_name
    -> AttributeValidator
AttributeValidator
    TABLE = _attr_name|TYPE|NUM
    PASSED -> AttributeManager_9
AttributeManager_9
    ATTR_TABLE:
      RENAME_SET_VALUE _attr_name > egenskap.typeId
      RENAME_SET_VALUE _attr_value > egenskap.verdi
      SET_TO egenskap.operasjon = FME_CONDITIONAL:DEFAULT_VALUE'_FME_NO_OP_'BOOL_OP;OR;COMPOSITE_TEST;<Unused>;TEST @Value(endringsflagg.Endringsflagg.typeEndring) = E'oppdater'FME_NUM_CONDITIONS2___
    -> egenskapXML [ROOT]
egenskapXML: XMLTemplater
    ROOT_QUERY_EXPR:
      {if( fme:has-attribute("egenskap.operasjon")) then
      <egenskap typeId="{fme:get-attribute("egenskap.typeId")}" operasjon="{fme:get-attribute("egenskap.operasjon")}">
          <verdi>{fme:get-attribute("egenskap.verdi")}</verdi>
      </egenskap>
      else
      <egenskap typeId="{fme:get-attribute("egenskap.typeId")}">
          <verdi>{fme:get-attribute("egenskap.verdi")}</verdi>
      </egenskap>}
    VISIBLE_QUERY_VALIDATE = Yes
    RESULT_ATTRIBUTE = egenskap.XML
    OUTPUT_XML_HEADER = No
    -> ListBuilder_2
ListBuilder_2
    LIST_NAME = egenskaper
    GRP_BY = tempId
    -> FeatureMerger_5 [SUPPLIER]

Bookmark: Opprydding i tekst
StringReplacer_3
    REGEXP = NO
    NO_MATCH = _FME_NO_OP_
    SRC_ATTRS = vegObjekt.XML
    FIND_TEXT = &lt;
    REPLACE_TEXT = <
    CASE = NO
    -> StringReplacer_4
StringReplacer_4
    REGEXP = NO
    NO_MATCH = _FME_NO_OP_
    SRC_ATTRS = vegObjekt.XML
    FIND_TEXT = &gt;
    REPLACE_TEXT = >
    CASE = NO
    -> AttributeRemover_4
AttributeRemover_4
    LIST_ATTRS = egenskaper{}
    -> vegObjekt
    -> ListBuilder_3

Bookmark: Opprydding
AttributeKeeper_7
    KEEP_ATTRS = endringsflagg.Endringsflagg.typeEndring,fme_basename,endringssett.XML
    -> StringReplacer_5
StringReplacer_5
    REGEXP = NO
    NO_MATCH = _FME_NO_OP_
    SRC_ATTRS = endringssett.XML
    FIND_TEXT = &lt;
    REPLACE_TEXT = <
    CASE = NO
    -> StringReplacer_6
StringReplacer_6
    REGEXP = NO
    NO_MATCH = _FME_NO_OP_
    SRC_ATTRS = endringssett.XML
    FIND_TEXT = &gt;
    REPLACE_TEXT = >
    CASE = NO
    -> ListBuilder_4

Bookmark: Opprydding
StringReplacer
    REGEXP = NO
    NO_MATCH = _FME_NO_OP_
    SRC_ATTRS = endringsliste.XML
    FIND_TEXT = &lt;
    REPLACE_TEXT = <
    CASE = NO
    -> StringReplacer_2
StringReplacer_2
    REGEXP = NO
    NO_MATCH = _FME_NO_OP_
    SRC_ATTRS = endringsliste.XML
    FIND_TEXT = &gt;
    REPLACE_TEXT = >
    CASE = NO
    -> XMLFormatter_2
XMLFormatter_2
    REMOVE_EMPTY_ELEMENT = Yes
    REMOVE_ALL_COMMENT = No
    XML_INPUT_TYPE = Attribute Specifying XML Text
    FORMATTING_CHOICE = Pretty-Print XML
    NAMESPACE_CLEANUP = No
    COLLAPSE_EMPTY_ELEMENT = No
    SCHEMALOC_CLEANUP = No
    XML_OUTPUT_TYPE = Attribute
    OUTPUT_ENCODING = utf-8
    LIST_NAME = _xml_error
    XML_ATTR_TEXT = endringsliste.XML
    REPLACE_TABS_WITH_SPACES = no
    WHITESPACE_HANDLING = Preserve all whitespace
    TEXT_INDENT = no
    XML_OUTPUT_ATTR = _xml_output
    INDENT_SIZE = 1
    PASSED -> Sampler [off]
    PASSED -> AttributeRenamer_4
