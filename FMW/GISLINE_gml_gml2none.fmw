FME workspace GISLINE_gml_gml2none.fmw

Parameters:
- SourceDataset_GML = C:\DATA\GLA\Data\1902\Lysmast.GML   # Source Geography Markup Language (GML) File(s)
- DestDataset_GML = C:\DATA\GLA\Data\Transformert\Transformert_Lysmast_Tromsø.gml   # Destination Geography Markup Language (GML) File

Readers:
- GML_1: GML from $(SourceDataset_GML)

Writers:
- GML_2: GML to $(DestDataset_GML)

Lysmast (reader GML_1)
    attributes: ENDRINGSFLAGG.ENDRET_TID xml_decimal(9,0), ENDRINGSFLAGG.ENDRET_TYPE xml_char(2), GEOMETRITYPE xml_decimal(2,0), KVALITET.MÅLEMETODE xml_decimal(3,0), NVDB_TOTALMASTELENGDE xml_decimal(7,5), NVDB_TYPE xml_char(8), OBJTYPE xml_char(8), OPPDATERINGSDATO xml_decimal(9,0)
    -> SchemaMapper_2
Lysmast (writer GML_2)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, type xml_buffer, produktnavn xml_buffer, ettergivendeMast xml_buffer, byggeår xml_int64, driftsmerking xml_buffer, fundamentering xml_buffer, boltavstandFotplate xml_buffer, diameter xml_int64, diameterTopp xml_int64,
      totalMastelengde xml_real64, utligger xml_buffer, vedlikeholdsansvarlig xml_buffer, utliggerarmensLengde xml_real64, kommentar{}.Kommentar.beskrivelse xml_buffer, kommentar{}.Kommentar.dokumentasjon{}.Dokumentasjon.dato xml_date, kommentar{}.Kommentar.dokumentasjon{}.Dokumentasjon.type xml_buffer, kommentar{}.Kommentar.dokumentasjon{}.Dokumentasjon.filnavn xml_buffer, kommentar{}.Kommentar.dokumentasjon{}.Dokumentasjon.hyperlink xml_buffer, kommentar{}.Kommentar.dokumentasjon{}.Dokumentasjon.tekst xml_buffer, kommentar{}.Kommentar.dokumentasjon{}.Dokumentasjon.ansvarlig xml_buffer, kommentar{}.Kommentar.dokumentasjon{}.Dokumentasjon.arkiveringskode xml_buffer, kommentar{}.Kommentar.dokumentasjon{}.Dokumentasjon.merknad xml_buffer, bardunStrever xml_buffer, overflatebehandling xml_buffer, rALKode xml_buffer, produsentnavn xml_buffer, eier xml_buffer, eierNavn xml_buffer, posisjon xml_geometry, dokumentasjon{}.Dokumentasjon.dato xml_date, dokumentasjon{}.Dokumentasjon.type xml_buffer, dokumentasjon{}.Dokumentasjon.filnavn xml_buffer, dokumentasjon{}.Dokumentasjon.hyperlink xml_buffer, dokumentasjon{}.Dokumentasjon.tekst xml_buffer, dokumentasjon{}.Dokumentasjon.ansvarlig xml_buffer, dokumentasjon{}.Dokumentasjon.arkiveringskode xml_buffer, dokumentasjon{}.Dokumentasjon.merknad xml_buffer

Bookmark: Oversetter til GML-navn
Note: Oversetter egenskapsnavn til GML-navn
SchemaMapper_2
    CSV__SCHEMA_WITH_COL_NAMES = ft_attr,char,17,,ftid,number,3,0,ptid,number,6,0,name,char,22,
    ROW_ID_ATTR = _schemamapper_row_ids
    MAP_ATTRS = ptid name """"""
    CSV__DUPLICATE_DELIMS = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXDESTATTR = fme_feature_type
    CSV__STRIP_QUOTES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_FIELD_NAMES = YES
    CSV__IN_SEPARATOR = ;
    IDXSOURCEATTR = fme_feature_type
    CSV__SKIP_LINES = 1
    CSV__SCHEMA = char,17,,number,3,0,number,6,0,char,22,
    IDXSOURCECOL = ""
    TABLE = CSV
    DATASET = $(FME_MF_DIR)glabelysning_ptSOSIMapping.csv
    CSV__ALLOW_SPACES_IN_COLUMN_NAMES = yes
    IDXDESTCOL = ""
    FORMAT = CSV
    CSV__SKIP_FOOTER = 0
    CSV_SCAN_MAX_FEATURES = 1000
    CSV__GROUP_BY_DATASET = no
    CSV__FIELD_NAMES_AFTER_HEADER = no
    MAPPED -> AttributeManager
    UNMAPPED -> AttributeManager
AttributeManager
    ATTR_TABLE:
      RENAME_SET_VALUE ENDRINGSFLAGG.ENDRET_TID > endringsflagg.Endringsflagg.tidspunktEndring
      RENAME_SET_VALUE ENDRINGSFLAGG.ENDRET_TYPE > endringsflagg.Endringsflagg.typeEndring
      RENAME_SET_VALUE KVALITET.MÅLEMETODE > kvalitet.Posisjonskvalitet.målemetode
      RENAME_SET_VALUE OPPDATERINGSDATO > oppdateringsdato
    -> NullAttributeMapper_3
NullAttributeMapper_3
    SOURCE_ATTR_VAL = Empty Null
    NULL_TREATMENT = Missing
    ATTRCHOICE = All Attributes
    -> DateFormatter
DateFormatter
    FMT = ISO DateTime (%Y-%m-%dT%H:%M:%S)
    SRCFMT = %Y%m%d
    DATE_ATTR = oppdateringsdato,endringsflagg.Endringsflagg.tidspunktEndring
    INVALID_DATE_VALUE = _FME_NO_OP_
    -> GeometryFilter

Bookmark: Definerer geometriegenskaper
GeometryFilter
    GEOM_PORT_NAMES = Point Line Area
    BREAK_AGG = No
    POINT -> GeometryPropertySetter
    LINE -> GeometryPropertySetter_4
    AREA -> GeometryPropertySetter_3
GeometryPropertySetter
    GEOM_NAME_FIELD = posisjon
    OVERWRITE_CHOICE = Yes
    SETTYPE_PARAM = Geometry Name
    SET -> Lysmast (writer GML_2)
GeometryPropertySetter_4
    GEOM_NAME_FIELD = senterlinje
    OVERWRITE_CHOICE = Yes
    SETTYPE_PARAM = Geometry Name
    SET -> AttributeRemover
AttributeRemover
    REMOVE_ATTRS = posisjon
    -> Lysmast (writer GML_2)
GeometryPropertySetter_3
    GEOM_NAME_FIELD = område
    OVERWRITE_CHOICE = Yes
    SETTYPE_PARAM = Geometry Name
    SET -> Lysmast (writer GML_2)
