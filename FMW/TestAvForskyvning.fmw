FME workspace TestAvForskyvning.fmw

Parameters:
- SourceDataset_GML = C:\DATA\GitHub\GLA\Data\501\20180508_Gatelys_Lillehammer.gml   # Source Geography Markup Language (GML) File(s)
- SourceDataset_GML_5 = ""C:\DATA\GitHub\NVDBGML\GML\kommune\501\87\Belysningspunkt.gml" "C:\DATA\GitHub\NVDBGML\GML\kommune\501\87\Belysningsstrekning.gml" "C:\DATA\GitHub\NVDBGML\GML\kommune\501\87\Lysarmatur.gml" "C:\DATA\GitHub\NVDBGML\GML\kommune\501\87\Lysmast.gml""   # Source Geography Markup Language (GML) File(s)
- SourceDataset_GML_4 = C:\DATA\GitHub\NVDBGML\GML\kommune\501\481\Tennpunkt.gml   # Source Geography Markup Language (GML) File(s)

Readers:
- GML_1: GML from $(SourceDataset_GML)
- GML_2: GML from $(SourceDataset_GML_5)
- GML_3: GML from $(SourceDataset_GML_4)

Belysningspunkt (reader GML_1)
    attributes: bruksområde xml_char(17), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), plassering xml_char(8), strømtilførselKategori xml_char(10), vedlikeholdsansvarlig xml_char(8)
    -> Reprojector
Lysarmatur (reader GML_1)
    attributes: driftsattår xml_decimal(5,0), driftsmerking xml_char(9), effekt xml_decimal(4,0), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(4,0), kvalitet.Posisjonskvalitet.synbarhet xml_decimal(2,0), lyskildeType xml_char(16), produktnavnArmatur xml_char(12), produsentnavnArmatur xml_char(14), vedlikeholdsansvarlig xml_char(8)
    -> Reprojector
Lysmast (reader GML_1)
    attributes: bruksområde xml_char(4), byggeår xml_decimal(5,0), driftsmerking xml_char(9), eier xml_char(8), eierNavn xml_char(20), endringsflagg.Endringsflagg.tidspunktEndring xml_char(11), endringsflagg.Endringsflagg.typeEndring xml_char(2), identifikasjon.Identifikasjon.lokalId xml_char(9), identifikasjon.Identifikasjon.navnerom xml_char(20), kvalitet.Posisjonskvalitet.målemetode xml_decimal(3,0), kvalitet.Posisjonskvalitet.nøyaktighet xml_decimal(3,0), kvalitet.Posisjonskvalitet.synbarhet xml_decimal(2,0), type xml_char(9), utligger xml_char(3), vedlikeholdsansvarlig xml_char(8)
    -> Reprojector
Tennpunkt (reader GML_1)
    attributes: driftsattår xml_decimal(5,0), driftsmerking xml_char(9), endringsflagg.Endringsflagg.tidspunktEndring xml_char(11), endringsflagg.Endringsflagg.typeEndring xml_char(2), identifikasjon.Identifikasjon.lokalId xml_char(6), identifikasjon.Identifikasjon.navnerom xml_char(20), kvalitet.Posisjonskvalitet.målemetode xml_decimal(3,0), kvalitet.Posisjonskvalitet.nøyaktighet xml_decimal(3,0), kvalitet.Posisjonskvalitet.synbarhet xml_decimal(2,0)
    -> Reprojector
Reprojector
    DEST = ETRS89.UTM-33N
    INTERPOLATION_TYPE_NAME = Nearest Neighbor
    RASTER_CELL_SIZE = Preserve Cells
    RASTER_TOLERANCE = 0.0
    SOURCE = Read from feature
    REPROJECTED -> CoordinateRounder
CoordinateRounder
    XPREC = 3
    YPREC = 3
    ZPREC = 3
    ROUNDED -> AttributeExposer
AttributeExposer
    ATTR_LIST = fme_feature_type
    -> org_
    -> NeighborFinder [BASE]
org_: Inspector [off]
    TACKATTRS = fme_feature_type
Belysningspunkt (reader GML_2)
    attributes: antall xml_decimal(2,0), assosiertLysarmatur.href xml_char(44), assosiertLysarmatur{}.href xml_char(44), assosiertLysmast.href xml_char(41), assosiertLysmast{}.href xml_char(41), assosiertTilstandSkade_Belysning.href xml_char(57), assosiertTilstandSkade_Belysning{}.href xml_char(57), avstandFraVegkant xml_decimal(4,1), bruksområde xml_char(23), eier xml_char(21), eier_Navn xml_char(20), fellesføringMedAnnenEtat xml_char(12), identifikasjon.Identifikasjon.lokalId xml_decimal(10,0), identifikasjon.Identifikasjon.navnerom xml_char(17), identifikasjon.Identifikasjon.versjonId xml_decimal(2,0), lineærPosisjon.LineærPosisjonPunkt.lineærReferanseMetode xml_char(12), lineærPosisjon.LineærPosisjonPunkt.nettverkselement.href xml_char(42), lineærPosisjon.LineærPosisjonPunkt.posisjon xml_decimal(31,17), plassering xml_char(21), prosesshistorie xml_char(62), strømtilførsel_Kategori xml_char(10), vedlikeholdsansvarlig xml_char(16), vegreferanse.Vegreferanse.hovedparsell xml_decimal(4,0), vegreferanse.Vegreferanse.vegkategori xml_char(2), vegreferanse.Vegreferanse.veglenkeMeterFra xml_decimal(6,0), vegreferanse.Vegreferanse.veglenkeMeterTil xml_decimal(6,0), vegreferanse.Vegreferanse.vegnummer xml_decimal(6,0), vegreferanse.Vegreferanse.vegstatus xml_char(2)
    -> AttributeExposer_2
Belysningsstrekning (reader GML_2)
    attributes: assosiertBelysningspunkt.href xml_char(49), assosiertBelysningspunkt{}.href xml_char(49), assosiertKommentar.href xml_char(43), avstand_Innbyrdes xml_decimal(3,0), bruksområde xml_char(23), byggeår xml_decimal(5,0), dimming xml_char(4), eier xml_char(21), fjernstyring xml_char(4), identifikasjon.Identifikasjon.lokalId xml_decimal(10,0), identifikasjon.Identifikasjon.navnerom xml_char(17), identifikasjon.Identifikasjon.versjonId xml_decimal(2,0), lineærPosisjon.LineærPosisjonStrekning.fraPosisjon xml_decimal(31,17), lineærPosisjon.LineærPosisjonStrekning.lineærReferanseMetode xml_char(12), lineærPosisjon.LineærPosisjonStrekning.nettverkselement.href xml_char(42), lineærPosisjon.LineærPosisjonStrekning.retning xml_char(4), lineærPosisjon.LineærPosisjonStrekning.tilPosisjon xml_decimal(19,17), lineærPosisjon{}.LineærPosisjonStrekning.fraPosisjon xml_decimal(18,16), lineærPosisjon{}.LineærPosisjonStrekning.lineærReferanseMetode xml_char(12), lineærPosisjon{}.LineærPosisjonStrekning.nettverkselement.href xml_char(42), lineærPosisjon{}.LineærPosisjonStrekning.retning xml_char(4), lineærPosisjon{}.LineærPosisjonStrekning.tilPosisjon xml_decimal(18,16), navnPåStrekning xml_char(17), prosesshistorie xml_char(62), type xml_char(22), vedlikeholdsansvarlig xml_char(16), vegreferanse.Vegreferanse.hovedparsell xml_decimal(4,0), vegreferanse.Vegreferanse.vegkategori xml_char(2), vegreferanse.Vegreferanse.veglenkeMeterFra xml_decimal(6,0), vegreferanse.Vegreferanse.veglenkeMeterTil xml_decimal(6,0),
      vegreferanse.Vegreferanse.vegnummer xml_decimal(4,0), vegreferanse.Vegreferanse.vegstatus xml_char(2), vegreferanse{}.Vegreferanse.hovedparsell xml_decimal(4,0), vegreferanse{}.Vegreferanse.vegkategori xml_char(2), vegreferanse{}.Vegreferanse.veglenkeMeterFra xml_decimal(6,0), vegreferanse{}.Vegreferanse.veglenkeMeterTil xml_decimal(6,0), vegreferanse{}.Vegreferanse.vegnummer xml_decimal(4,0), vegreferanse{}.Vegreferanse.vegstatus xml_char(2)
    -> AttributeExposer_2
Lysarmatur (reader GML_2)
    attributes: antallArmaturerIBelysningspkt xml_decimal(2,0), antallLyskilderPerArmatur xml_decimal(2,0), armaturnummer xml_char(6), avskjerming_Materiale xml_char(6), avskjerming_Type xml_char(18), dimming xml_char(4), driftsattår xml_decimal(5,0), driftsmerking xml_char(9), effekt xml_decimal(5,1), eier xml_char(21), eier_Navn xml_char(20), høydeOverVeg xml_decimal(4,1), identifikasjon.Identifikasjon.lokalId xml_decimal(10,0), identifikasjon.Identifikasjon.navnerom xml_char(17), identifikasjon.Identifikasjon.versjonId xml_decimal(2,0), lineærPosisjon.LineærPosisjonPunkt.lineærReferanseMetode xml_char(12), lineærPosisjon.LineærPosisjonPunkt.nettverkselement.href xml_char(42), lineærPosisjon.LineærPosisjonPunkt.posisjon xml_decimal(31,17), lyskildeType xml_char(17), produktnavn_Armatur xml_char(17), produsentnavn_Armatur xml_char(17), prosesshistorie xml_char(62), utskiftbareLyskilder xml_char(3), utstyrsklasse xml_char(15), vedlikeholdsansvarlig xml_char(16), vegreferanse.Vegreferanse.hovedparsell xml_decimal(4,0), vegreferanse.Vegreferanse.vegkategori xml_char(2), vegreferanse.Vegreferanse.veglenkeMeterFra xml_decimal(6,0), vegreferanse.Vegreferanse.veglenkeMeterTil xml_decimal(6,0), vegreferanse.Vegreferanse.vegnummer xml_decimal(5,0),
      vegreferanse.Vegreferanse.vegstatus xml_char(2)
    -> AttributeExposer_2
Lysmast (reader GML_2)
    attributes: RAL_Kode xml_decimal(5,0), bardunStrever xml_char(4), boltavstandFotplate xml_char(14), bruksområde xml_char(4), byggeår xml_decimal(5,0), diameter xml_decimal(4,0), driftsmerking xml_char(9), eier xml_char(21), eier_Navn xml_char(20), ettergivendeMast xml_char(22), fundamentering xml_char(16), identifikasjon.Identifikasjon.lokalId xml_decimal(10,0), identifikasjon.Identifikasjon.navnerom xml_char(17), identifikasjon.Identifikasjon.versjonId xml_decimal(2,0), lineærPosisjon.LineærPosisjonPunkt.lineærReferanseMetode xml_char(12), lineærPosisjon.LineærPosisjonPunkt.nettverkselement.href xml_char(42), lineærPosisjon.LineærPosisjonPunkt.posisjon xml_decimal(31,17), overflatebehandling xml_char(12), produsentnavn xml_char(9), prosesshistorie xml_char(62), totalMastelengde xml_decimal(4,1), type xml_char(24), utligger xml_char(4), utliggerarmensLengde xml_decimal(3,1), vedlikeholdsansvarlig xml_char(16), vegreferanse.Vegreferanse.hovedparsell xml_decimal(4,0), vegreferanse.Vegreferanse.vegkategori xml_char(2), vegreferanse.Vegreferanse.veglenkeMeterFra xml_decimal(6,0), vegreferanse.Vegreferanse.veglenkeMeterTil xml_decimal(6,0), vegreferanse.Vegreferanse.vegnummer xml_decimal(5,0),
      vegreferanse.Vegreferanse.vegstatus xml_char(2)
    -> AttributeExposer_2
Tennpunkt (reader GML_3)
    attributes: driftsattår xml_decimal(5,0), driftsmerking xml_char(9), identifikasjon.Identifikasjon.lokalId xml_decimal(10,0), identifikasjon.Identifikasjon.navnerom xml_char(17), identifikasjon.Identifikasjon.versjonId xml_decimal(2,0), lineærPosisjon.LineærPosisjonPunkt.lineærReferanseMetode xml_char(12), lineærPosisjon.LineærPosisjonPunkt.nettverkselement.href xml_char(42), lineærPosisjon.LineærPosisjonPunkt.posisjon xml_decimal(17,15), prosesshistorie xml_char(32), spenning xml_decimal(4,0), tennpunktnummer xml_decimal(9,0), vegreferanse.Vegreferanse.hovedparsell xml_decimal(2,0), vegreferanse.Vegreferanse.vegkategori xml_char(2), vegreferanse.Vegreferanse.veglenkeMeterFra xml_decimal(5,0), vegreferanse.Vegreferanse.veglenkeMeterTil xml_decimal(5,0), vegreferanse.Vegreferanse.vegnummer xml_decimal(5,0), vegreferanse.Vegreferanse.vegstatus xml_char(2)
    -> AttributeExposer_2
AttributeExposer_2
    ATTR_LIST = fme_feature_type
    -> NVDB_
    -> NeighborFinder [CANDIDATE]
NeighborFinder
    CANDIDATES_FIRST = No
    GROUP_BY = fme_feature_type
    INSERT_VERTEX = No
    K = 1
    MAX = 2
    MEASURES_FROM_CANDIDATE = Yes
    MEASURE_TYPE = Continuous
    MODE = Bases and Candidates
    TREAT_POLYGON_AS = Lines
    MATCHED -> kobla
kobla: Inspector
    TACKATTRS = fme_feature_type
NVDB_: Inspector [off]
    TACKATTRS = fme_feature_type
