FME workspace 20170516_GML2API_MedFjerningAvAssosiasjoner.fmw

Parameters:
- SourceDataset_GML = C:\DATA\GitHub\GLA\Data\1902\20170403\Samle_45.gml   # Source Geography Markup Language (GML) File(s)
- omrNvn = 1902   # Område
- wFolder = C:\DATA\GitHub\GLA\Data   # Arbeidsmappe
- vegkategori = K   # Vegkategori
- DestDataset_CSV2 = C:\DATA\GitHub\GLA\Data\XML   # Destination CSV (Comma Separated Value) Folder
- SourceDataset_CSV2 = C:\DATA\GitHub\GLA\Data\XML\Assosiasjoner.csv   # Source CSV (Comma Separated Value) File(s)
- omr = kommune   # Områdetype
- DakatVersjon = 2.07   # Datakatalogversjon

Readers:
- GML_1: GML from $(SourceDataset_GML)
- CSV2_1: CSV2 from $(SourceDataset_CSV2)

Writers:
- TEXTLINE_1: TEXTLINE to $(wFolder)\XML\Belysningsdata.xml
- CSV2_2: CSV2 to $(DestDataset_CSV2)

Lysarmatur (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedparsell xml_int64, vegreferanse{}.Vegreferanse.veglenkeMeterFra xml_int64, vegreferanse{}.Vegreferanse.veglenkeMeterTil xml_int64, vegreferanse{}.Vegreferanse.referanseretning xml_buffer, vegreferanse{}.Vegreferanse.vegreferanseFraDato xml_date, vegreferanse{}.Vegreferanse.vegreferanseTilDato xml_date, lyskildeType xml_buffer, effekt xml_real64, driftsmerking xml_buffer, driftsattår xml_int64,
      høydeOverVeg xml_real64, antallLyskilderPerArmatur xml_buffer, antallArmaturerIBelysningspkt xml_buffer, inngårINødsystemet xml_buffer, produktnavnArmatur xml_buffer, produsentnavnArmatur xml_buffer, produsentnavnDriver xml_buffer, produsentnavnLyskilde xml_buffer, optikk xml_buffer, konstantLysutbytte xml_buffer, dimming xml_buffer, utystyrsklasse xml_buffer, driftsstrømUdimmet xml_int64, lysflux xml_int64, LEDEffektArmaturTotalt_Test xml_int64, fargetemperatur xml_int64, LEDAntallDioder xml_int64, LEDEffektPerStk_Test xml_real64, avskjermingType xml_buffer, avskjermingMateriale xml_buffer, fargegjengivelsesindeks xml_int64, utskiftbareLyskilder xml_buffer, armaturnummer xml_buffer, kommunikasjonsenhet xml_buffer, eier xml_buffer, eierNavn xml_buffer, vedlikeholdsansvarlig xml_buffer, posisjon xml_geometry, felt xml_buffer, lineærPosisjon{}.LineærPosisjonPunkt.lineærReferanseMetode xml_buffer,
      lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer, lineærPosisjon{}.LineærPosisjonPunkt.nettverkselement.owns xml_boolean, lineærPosisjon{}.LineærPosisjonPunkt.posisjon xml_real64, assosiertDokumentasjon{}.owns xml_boolean, assosiertDokumentasjon{}.nilReason xml_buffer, assosiertDokumentasjon{}.gml_remoteSchema xml_buffer, assosiertDokumentasjon{}.xlink_href xml_buffer, assosiertKommentar{}.owns xml_boolean, assosiertKommentar{}.nilReason xml_buffer, assosiertKommentar{}.gml_remoteSchema xml_buffer, assosiertKommentar{}.xlink_href xml_buffer
    -> DateFormatter
DateFormatter
    FMT = %Y
    DATE_ATTR = driftsattår
    SRCFMT = Unknown - Automatic Detection
    INVALID_DATE_VALUE = _FME_NO_OP_
    -> org
    -> AttributeManager
org: Inspector
    TACKATTRS = fme_feature_type
AttributeManager
    ATTR_TABLE = SET_TO objekttype = @Value(fme_feature_type)
    -> SchemaMapper
    -> Snapper_2 [off]
    -> AttributeManager_16
Note: Setter alle som "E" (etter at alle nye er lest inn i egen transaksjon)
AttributeManager_16
    ATTR_TABLE = SET_TO endringsflagg.Endringsflagg.typeEndring = E
    -> Snapper_2
Snapper_2
    EXTEND_LINES = NEVER
    SNAPTYPE_PARAM = End Point Snapping
    SAVE_SHORT_LINES = No
    TOLERANCE = 0.3
    SNAPPED -> Vegnettposisjon
    UNTOUCHED -> Vegnettposisjon
Note: Posisjon i vegnettet
Vegnettposisjon
    vegkategori = $(vegkategori)
    -> TestFilter
Note: Skiller melllom nye objekter og objekter som skal endres
TestFilter
    TEST_LIST = BOOL_OP,OR,COMPOSITE_TEST,<Unused>,TEST_CLAUSE,"TEST @Value(endringsflagg.Endringsflagg.typeEndring) != E",Ny
    DEFAULT_VALUE = Endring
    Ny -> SchemaMapper_2
    Endring -> NeighborFinder [BASE]
Note: Kobler endirngsobjekter til eksisterende fra NVDB
NeighborFinder
    INSERT_VERTEX = No
    ATTR_ACCUM_MODE = Merge Candidate
    MODE = Bases and Candidates
    ATTR_CONFLICT_RES = Use Base
    K = 1
    TREAT_POLYGON_AS = Lines
    CANDIDATES_FIRST = No
    MAX = 10
    GROUP_BY = fme_feature_type
    MATCHED -> SchemaMapper_2
    UNMATCHED_BASE -> AttributeManager_3
Mapped: Inspector
    TACKATTRS = endringsflagg.Endringsflagg.typeEndring fme_feature_type
AttributeManager_2
    ATTR_TABLE = SET_TO assosiasjoner.antall = 0
    -> Counter_3
Counter_3
    START = 1
    CNT_ATTR = tempId
    SCOPE = Global
    DOMAIN = counter
    -> AttributeManager_14
AttributeManager_14
    ATTR_TABLE = SET_TO tempId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
    -> NullAttributeMapper
NullAttributeMapper
    ATTRCHOICE = All Attributes
    NULL_TREATMENT = Missing
    OTHER_VALUE = 0
    SOURCE_ATTR_VAL = Null Empty "Missing (Selected Attributes Only)"
    -> AttributeExploder
    -> FeatureMerger_5 [REQUESTOR]
Note: Kobler liste med egenskaper til objektet
FeatureMerger_5
    REJECT_NULL_MISSING_KEYS = No
    ATTR_ACCUM_MODE = Merge Supplier
    IGNORE_NULLS = No
    ATTR_CONFLICT_RES = Use Requestor
    MERGE_TYPE = Attributes Only
    SUPPLIERS_FIRST = No
    PROCESS_DUPS = No
    JOIN_KEYS = @Value(tempId) @Value(tempId) AUTO
    MERGED -> AttributeManager_12
Note: Tilpasninger på vegObjektnivå
AttributeManager_12
    ATTR_TABLE:
      SET_TO vegObjekt.typeId = @Value(fme_feature_type)
      SET_TO vegObjekt.tempId = FME_CONDITIONAL:DEFAULT_VALUE'_FME_NO_OP_'BOOL_OP;OR;COMPOSITE_TEST;<Unused>;TEST @Value(endringsflagg.Endringsflagg.typeEndring) = N'@Value(tempId)'FME_NUM_CONDITIONS2___
      SET_TO vegObjekt.nvdbId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
      SET_TO vegObjekt.versjon = FME_CONDITIONAL:DEFAULT_VALUE'_FME_NO_OP_'BOOL_OP;OR;COMPOSITE_TEST;<Unused>;TEST @Value(endringsflagg.Endringsflagg.typeEndring) = E'@Value(identifikasjon.Identifikasjon.versjonId)'FME_NUM_CONDITIONS2___
    -> assosiasjonXML_2 [ROOT]
    -> FeatureMerger [REQUESTOR]
    -> AttributeFilter_3 [off]
    -> NullAttributeMapper_2 [off]
NVDB: Inspector
    TACKATTRS = fme_feature_type
Note: Tidligere assosiasjoner som skal gjenopprettes
CSV (reader CSV2_1) [off]
    attributes: MorId string, DatterID string, AssosiasjonsID string
    -> assosiasjonXML_3 [ROOT]
Note: Lager assosiasjons-XML for objektet, til senere bruk
assosiasjonXML_3: XMLTemplater
    ROOT_QUERY_EXPR = <nvdbId>{fme:get-attribute("DatterID")}</nvdbId>
    OUTPUT_XML_HEADER = No
    RESULT_ATTRIBUTE = assosiasjon.XML
    VISIBLE_QUERY_VALIDATE = Yes
    -> ListBuilder_5
ListBuilder_5
    GROUP_BY = MorId AssosiasjonsID
    LIST_NAME = assosiasjoner
    LIST_ATTRS_TO_INCLUDE = assosiasjon.XML
    -> assosiasjonXML_4 [ROOT]
assosiasjonXML_4: XMLTemplater
    ROOT_QUERY_EXPR:
      <assosiasjon typeId="{fme:get-attribute("AssosiasjonsID")}" operasjon="oppdater">
          {fme:get-list-attribute("assosiasjoner{}.assosiasjon.XML")}
      </assosiasjon>
    OUTPUT_XML_HEADER = No
    RESULT_ATTRIBUTE = assosiasjoner.XML
    VISIBLE_QUERY_VALIDATE = Yes
    -> AttributeManager_15
AttributeManager_15
    ATTR_TABLE = RENAME_SET_VALUE MorId > tempId
    -> StringReplacer_8
NullAttributeMapper_2
    ATTRCHOICE = Selected Attributes
    NEW_VALUE = 0
    NULL_TREATMENT = New Value
    ATTRLIST = assosiasjoner.antall
    SOURCE_ATTR_VAL = Null Empty "Missing (Selected Attributes Only)"
    -> StringFormatter
StringFormatter
    FORMAT = d
    SRC_ATTRS = assosiasjoner.antall
    -> AttributeValueMapper
Note: Håndtering av geometriegenskap må forbedres. Pr nå er denne "hardkoda" i AttributeValueMapper
Note: Geometriegenskap
AttributeValueMapper
    DIRECTION = Forward (Source To Destination)
    LUT = 86,4786,87,4787,88,4788,181,4838
    SRC = fme_feature_type
    VAL_ATTR = _geometriegenskap
    -> vegObjektXML [ROOT]
vegObjektXML: XMLTemplater
    ROOT_QUERY_EXPR:
      {if( fme:has-attribute("vegObjekt.nvdbId")) then
          <vegObjekt typeId="{fme:get-attribute("vegObjekt.typeId")}" nvdbId="{fme:get-attribute("vegObjekt.nvdbId")}" versjon="{fme:get-attribute("vegObjekt.versjon")}">
              <egenskaper>
              {fme:get-list-attribute("egenskaper{}.egenskap.XML")}
              {if( fme:has-attribute("_geometry")) then
              <egenskap typeId="{fme:get-attribute("_geometriegenskap")}" operasjon="oppdater">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}

              <lokasjon operasjon="oppdater">
                  {fme:get-attribute("lokasjon")}
              </lokasjon>
          </vegObjekt>
      else
          <vegObjekt typeId="{fme:get-attribute("vegObjekt.typeId")}" tempId="-{fme:get-attribute("tempId")}">
              <egenskaper>
              {fme:get-list-attribute("egenskaper{}.egenskap.XML")}
              {if( fme:has-attribute("_geometry")) then
              <egenskap typeId="{fme:get-attribute("_geometriegenskap")}">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}
              <lokasjon>
                  {fme:get-attribute("lokasjon")}
              </lokasjon>
          </vegObjekt>}
    OUTPUT_XML_HEADER = No
    RESULT_ATTRIBUTE = vegObjekt.XML
    VISIBLE_QUERY_VALIDATE = Yes
    -> Sorter
Sorter
    SORT_PARM = vegObjekt.typeId NUMERIC ASCENDING
    SORTED -> StringReplacer_3
ListBuilder_3
    GROUP_BY = endringsflagg.Endringsflagg.typeEndring
    LIST_NAME = vegObjektliste
    -> EndringssettXML [ROOT]
EndringssettXML: XMLTemplater
    ROOT_QUERY_EXPR:
        {if( {fme:get-attribute("endringsflagg.Endringsflagg.typeEndring")}="E") then
        <delvisKorriger>
          <vegObjekter>
          {fme:get-list-attribute("vegObjektliste{}.vegObjekt.XML")}
          </vegObjekter>
        </delvisKorriger>
        else if( {fme:get-attribute("endringsflagg.Endringsflagg.typeEndring")}="N") then
        <registrer>
          <vegObjekter>
          {fme:get-list-attribute("vegObjektliste{}.vegObjekt.XML")}
          </vegObjekter>
        </registrer>
        else ()}
    OUTPUT_XML_HEADER = No
    RESULT_ATTRIBUTE = endringssett.XML
    VISIBLE_QUERY_VALIDATE = Yes
    -> AttributeKeeper_7
ListBuilder_4
    LIST_NAME = endringsliste
    -> TimeStamper
TimeStamper
    TIME_ATTR = _timestamp
    FMT = ^Y-^m-^d
    -> EndringslisteXML [ROOT]
EndringslisteXML: XMLTemplater
    ROOT_QUERY_EXPR:
      <endringssett xmlns="http://nvdb.vegvesen.no/apiskriv/domain/v2" effektDato="{fme:get-attribute("_timestamp")}" datakatalogversjon="$(DakatVersjon)">
      {fme:get-list-attribute("endringsliste{}.endringssett.XML")}
      </endringssett>
    OUTPUT_XML_HEADER = No
    RESULT_ATTRIBUTE = endringsliste.XML
    VISIBLE_QUERY_VALIDATE = Yes
    -> StringReplacer
Sampler
    RATE = 1
    SAMPLE_TYPE_LONG = Every Nth Feature
    GROUP_BY = fme_feature_type
    SAMPLE_MODE = No
    SAMPLED -> AttributeRenamer_4
AttributeRenamer_4
    ATTR_TABLE = RENAME_SET_DEFAULT _xml_output > text_line_data
    -> text_line (writer TEXTLINE_1)
text_line (writer TEXTLINE_1)
    attributes: text_line_data buffer

Bookmark: Eksisterende objekter i NVDB
Note: Mapper objekttypenavn til VOT-ID vha mappingtabell ftMapping / - for å finne aktuellle objekttyper
SchemaMapper
    CSV__ALLOW_SPACES_IN_COLUMN_NAMES = yes
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCEATTR = fme_feature_type
    CSV__SCHEMA = number,3,0,char,18,
    CSV__SCHEMA_WITH_COL_NAMES = ftid,number,3,0,name,char,18,
    IDXSOURCECOL = name
    DATASET = C:\DATA\GitHub\GLA\XSD\glabelysning_ftMapping.csv
    CSV__SKIP_LINES = 1
    IDXDESTCOL = ftid
    CSV__DUPLICATE_DELIMS = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    ROW_ID_ATTR = _schemamapper_row_ids
    CSV__IN_FIELD_NAMES = YES
    IDXDESTATTR = fme_feature_type
    CSV_SCAN_MAX_FEATURES = 1000
    TABLE = CSV
    CSV__STRIP_QUOTES = yes
    CSV__SKIP_FOOTER = 0
    CSV__FIELD_NAMES_AFTER_HEADER = no
    CSV__GROUP_BY_DATASET = no
    MAPPED -> DuplicateFilter
DuplicateFilter
    INPUT_ORDERED_CHOICE = No
    KEYATTR = fme_feature_type
    UNIQUE -> WorkspaceRunner
    UNIQUE -> FeatureReader [INITIATOR] [off]
Note: Eksporterer eksisterende fra NVDB til GML
WorkspaceRunner
    WORKSPACE_PARAMETERS = ftID,@Value(fme_feature_type),omr,$(omr),omrNvn,$(omrNvn),gmlFolder,$(wFolder),dwnlAssObj,Nei
    WORKSPACE_FILE = $(FME_MF_DIR)NVDBAPI2GML_V2_2017.fmw
    BLOCKING = Yes
    SUCCEEDED -> FeatureReader [INITIATOR]
Note: Leser eksisterende NVDB-objekter fra GML
FeatureReader
    GML_DISABLE_XML_NAMESPACE_PROCESSING = NO
    OUTPUT_FEATURES_DISPLAY = Schema and Data Features
    GML_XML_FRAGMENTS_AS_DOCUMENTS = YES
    GML_MULTI_VALUE_SIMPLE_PROPERTIES_AS_CSV = no
    ATTR_ACCUM_MODE = Only Use Result
    FORMAT = GML
    GML_USE_SEARCH_ENVELOPE = NO
    GML_IGNORE_APPLICATON_SCHEMA = no
    GML_MAP_EMBEDDED_OBJECTS_AS = ATTRIBUTES
    GML_MAP_ALL_SUBSTITUTABLE_PROPERTIES = YES
    GML_USE_OLD_READER = NO
    GML_DISABLE_AUTOMATIC_READER_TYPE_SELECTION = NO
    GML_CLIP_TO_ENVELOPE = NO
    GML_FEATURE_TYPES_SCHEMA_MODE = XML_SCHEMA
    GML_VALIDATE_DATASET = no
    GML_MAP_GEOMETRY_COLUMNS = YES
    GML_MAP_COMPLEX_PROPERTIES_AS = Nested Attributes
    DATASET = $(wFolder)\$(omr)\$(omrNvn)\@Value(fme_feature_type)\@Value(objekttype).gml
    GML_SKIP_SCHEMA_LOCATION_IN_DATASET = No
    GML_MAP_PREDEFINED_GML_PROPERTIES = NO
    COMBINE_GEOM = Use Result
    INTERACT = <No Spatial Filter>
    GML_FLATTEN_XML_FRAGMENTS = NO
    GML_ADD_GEOMETRIES_AS_XML_FRAGMENTS = NO
    GML_CONTINUE_ON_GEOM_ERROR = yes
    GML_CACHE_XSD = yes
    GML_ENFORCE_PATH_CONTINUITY_BY = SNAPPING_END_POINTS
    <OTHER> -> AttributeExposer
AttributeExposer
    ATTR_LIST = fme_feature_type,vegreferanse{}.Vegreferanse.vegkategori,identifikasjon.Identifikasjon.lokalId,identifikasjon.Identifikasjon.versjonId,lineærPosisjon{}.LineærPosisjonPunkt.nettverkselement.xlink_href
    -> ListSearcher
Note: Begrenser til objekter på valgt vegkategori
ListSearcher
    ATTR_VALUE = $(vegkategori)
    SEARCH_TYPE = First exact match
    LIST_ATTR = vegreferanse{}.Vegreferanse.vegkategori
    INDEX_ATTR = _list_index
    FOUND -> NVDB
    FOUND -> NeighborFinder [CANDIDATE]

Bookmark: Mapping til Datakatalog-IDer
Note: Setter endringstype = N for de som ikke blir kobla
AttributeManager_3
    ATTR_TABLE = SET_TO endringsflagg.Endringsflagg.typeEndring = N
    -> Endring_uten_eksisterende
    -> SchemaMapper_2
Note: Mapper objekttypenavn til VOT-ID vha mappingtabell ftMapping
SchemaMapper_2
    CSV__ALLOW_SPACES_IN_COLUMN_NAMES = yes
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCEATTR = fme_feature_type
    CSV__SCHEMA = number,3,0,char,18,
    CSV__SCHEMA_WITH_COL_NAMES = ftid,number,3,0,name,char,18,
    IDXSOURCECOL = name
    DATASET = C:\DATA\GitHub\GLA\XSD\glabelysning_ftMapping.csv
    CSV__SKIP_LINES = 1
    IDXDESTCOL = ftid
    CSV__DUPLICATE_DELIMS = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    ROW_ID_ATTR = _schemamapper_row_ids
    CSV__IN_FIELD_NAMES = YES
    IDXDESTATTR = fme_feature_type
    CSV_SCAN_MAX_FEATURES = 1000
    TABLE = CSV
    CSV__STRIP_QUOTES = yes
    CSV__SKIP_FOOTER = 0
    CSV__FIELD_NAMES_AFTER_HEADER = no
    CSV__GROUP_BY_DATASET = no
    MAPPED -> AttributeExposer_2
AttributeExposer_2
    ATTR_LIST = fme_feature_type
    -> SchemaMapper_3
Note: Mapper egenskapsnavn til ET-ID vha mappingtabell ptMapping
SchemaMapper_3
    CSV__ALLOW_SPACES_IN_COLUMN_NAMES = yes
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXSOURCEATTR = fme_feature_type
    CSV__SCHEMA = char,17,,number,4,0,number,6,0,char,43,
    CSV__SCHEMA_WITH_COL_NAMES = ft_attr,char,17,,ftid,number,4,0,ptid,number,6,0,name,char,43,
    IDXSOURCECOL = ""
    DATASET = C:\DATA\GitHub\GLA\XSD\glabelysning_ptMapping.csv
    CSV__SKIP_LINES = 1
    IDXDESTCOL = ""
    CSV__DUPLICATE_DELIMS = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    ROW_ID_ATTR = _schemamapper_row_ids
    MATCH_ATTRS = ft_attr ftid
    MAP_ATTRS = name ptid $(FME_ASC_16)
    CSV__IN_FIELD_NAMES = YES
    IDXDESTATTR = fme_feature_type
    CSV_SCAN_MAX_FEATURES = 1000
    TABLE = CSV
    CSV__STRIP_QUOTES = yes
    CSV__SKIP_FOOTER = 0
    CSV__FIELD_NAMES_AFTER_HEADER = no
    CSV__GROUP_BY_DATASET = no
    MAPPED -> SchemaMapper_4
Note: Oversetter tillatte verdier til NVDB-tekstverdier
SchemaMapper_4
    CSV__ALLOW_SPACES_IN_COLUMN_NAMES = yes
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    IDXSOURCEATTR = fme_feature_type
    CSV__SCHEMA = number,6,0,number,6,0,char,29,,char,34,
    CSV__SCHEMA_WITH_COL_NAMES = ptid,number,6,0,enid,number,6,0,name,char,29,,fullname,char,34,
    IDXSOURCECOL = ""
    DATASET = C:\DATA\GitHub\GLA\XSD\glabelysning_enMapping.csv
    CSV__SKIP_LINES = 1
    IDXDESTCOL = ""
    CSV__DUPLICATE_DELIMS = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    FORMAT = CSV
    ROW_ID_ATTR = _schemamapper_row_ids
    MATCH_ATTRS = ptid name
    MAP_ATTRS = name ptid fullname
    CSV__IN_FIELD_NAMES = YES
    IDXDESTATTR = fme_feature_type
    CSV_SCAN_MAX_FEATURES = 1000
    TABLE = CSV
    CSV__STRIP_QUOTES = yes
    CSV__SKIP_FOOTER = 0
    CSV__FIELD_NAMES_AFTER_HEADER = no
    CSV__GROUP_BY_DATASET = no
    MAPPED -> CoordinateRounder
Endring_uten_eksisterende: Inspector
    TACKATTRS = fme_feature_type

Bookmark: Lager geometristreng
CoordinateRounder
    ZPREC = 3
    YPREC = 3
    XPREC = 3
    ROUNDED -> CoordinateConcatenator
CoordinateConcatenator
    ELEMENT_DELIM = " "
    COORD_DELIM = ,
    COORD_ATTR = _coordinates
    COORDINATES_TO_INCLUDE_DIS = X Y Z
    PRECISION = No
    -> StringReplacer_7
StringReplacer_7
    FIND_TEXT = " -99999"
    CASE = NO
    SRC_ATTRS = _coordinates
    REGEXP = NO
    NO_MATCH = _FME_NO_OP_
    -> GeometryFilter
GeometryFilter
    GEOM_PORT_NAMES = Point Line
    BREAK_AGG = No
    POINT -> StringConcatenator_2
    LINE -> StringConcatenator
StringConcatenator_2
    PARM_LINE = POINT(@Value(_coordinates))
    VAL_ATTR = _geometry
    ACTION = Create New Attribute
    -> StringConcatenator_2_OUTPUT_-__PythonCaller
StringConcatenator
    PARM_LINE = LINESTRING(@Value(_coordinates))
    VAL_ATTR = _geometry
    ACTION = Create New Attribute
    -> StringConcatenator_2_OUTPUT_-__PythonCaller
StringConcatenator_2_OUTPUT_-__PythonCaller: Junction
    -> PythonCaller
Note: Kvalitetsstreng
PythonCaller
    PYTHONSYMBOL = setQuality
    PYTHONSOURCE:
      import fmeobjects
      # Template Function interface:

      def setQuality(feature):
          qs=""
          qm = feature.getAttribute('kvalitet.Posisjonskvalitet.målemetode')
          qms=str(qm)
          if qms <> "None":
              qs="målemetode="+qms

          qm = feature.getAttribute('kvalitet.Posisjonskvalitet.nøyaktighet')
          qms=str(qm)
          if qms <> "None":
              qs=qs+"; nøyaktighet="+qms

          qm = feature.getAttribute('kvalitet.Posisjonskvalitet.synbarhet')
          qms=str(qm)
          if qms <> "None":
              qs=qs+"; synbarhet="+qms

          qm = feature.getAttribute('kvalitet.Posisjonskvalitet.målemetodeHøyde')
          qms=str(qm)
          if qms <> "None":
              qs=qs+"; målemetodeHøyde="+qms

          qm = feature.getAttribute('kvalitet.Posisjonskvalitet.nøyaktighetHøyde')
          qms=str(qm)
          if qms <> "None":
              qs=qs+"; nøyaktighetHøyde="+qms

          if qs <> "":
              feature.setAttribute('qualityString', qs+'; ')
    NEW_ATTRIBUTES = qualityString
    -> Mapped
    -> AttributeManager_2

Bookmark: Liste med egenskaper
AttributeExploder
    ATTR_VALUE_LABEL = _attr_value
    EXPLODING_TYPE = Features
    ATTR_NAME_LABEL = _attr_name
    KEEP_GEOMETRY = No
    KEEP_ATTRIBUTES = Yes
    -> AttributeKeeper_5
AttributeKeeper_5
    KEEP_ATTRS = endringsflagg.Endringsflagg.typeEndring,_attr_value,tempId,_attr_name
    -> AttributeValidator
AttributeValidator
    TABLE = _attr_name;TYPE;NUM
    PASSED -> AttributeManager_9
AttributeManager_9
    ATTR_TABLE:
      RENAME_SET_VALUE _attr_name > egenskap.typeId
      RENAME_SET_VALUE _attr_value > egenskap.verdi
      SET_TO egenskap.operasjon = FME_CONDITIONAL:DEFAULT_VALUE'_FME_NO_OP_'BOOL_OP;OR;COMPOSITE_TEST;<Unused>;TEST @Value(endringsflagg.Endringsflagg.typeEndring) = E'oppdater'FME_NUM_CONDITIONS2___
    -> egenskapXML [ROOT]
egenskapXML: XMLTemplater
    ROOT_QUERY_EXPR:
      {if( fme:has-attribute("egenskap.operasjon")) then
      <egenskap typeId="{fme:get-attribute("egenskap.typeId")}" operasjon="{fme:get-attribute("egenskap.operasjon")}">
          <verdi>{fme:get-attribute("egenskap.verdi")}</verdi>
      </egenskap>
      else
      <egenskap typeId="{fme:get-attribute("egenskap.typeId")}">
          <verdi>{fme:get-attribute("egenskap.verdi")}</verdi>
      </egenskap>}
    OUTPUT_XML_HEADER = No
    RESULT_ATTRIBUTE = egenskap.XML
    VISIBLE_QUERY_VALIDATE = Yes
    -> ListBuilder_2
ListBuilder_2
    GROUP_BY = tempId
    LIST_NAME = egenskaper
    -> FeatureMerger_5 [SUPPLIER]

Bookmark: Etablering av assosiasjoner
Note: Lager assosiasjons-XML for objektet, til senere bruk
assosiasjonXML_2: XMLTemplater
    ROOT_QUERY_EXPR:
      {if( {fme:get-attribute("endringsflagg.Endringsflagg.typeEndring")}="E") then
      <nvdbId>{fme:get-attribute("vegObjekt.nvdbId")}</nvdbId>
      else
      <tempId>-{fme:get-attribute("vegObjekt.tempId")}</tempId>}
    OUTPUT_XML_HEADER = No
    RESULT_ATTRIBUTE = assosiasjon.XML
    VISIBLE_QUERY_VALIDATE = Yes
    -> AttributeFilter
AttributeFilter
    ATTR_VALUES = <Empty>,<Missing>,<Null>,<Unfiltered>,Belysningsstrekning,Belysningspunkt,Lysmast,Lysarmatur
    ATTR_NAME = objekttype
    Belysningsstrekning -> SpatialRelator [Requestor]
    Belysningspunkt -> Bufferer
    Belysningspunkt -> SpatialRelator_2 [Requestor]
    Belysningspunkt -> SpatialRelator_3 [Requestor]
    Lysmast -> AttributeFilter_Lysmast_-__AttributeValueMapper
    Lysmast -> Bufferer_2
    Lysarmatur -> AttributeFilter_Lysmast_-__AttributeValueMapper
    Lysarmatur -> Bufferer_3
Bufferer
    OFFSET = 1
    CAP_STYLE = Round
    CORNER_STYLE = Round
    ANGLE = 22.5
    BUFFERED -> SpatialRelator [Supplier]
SpatialRelator
    LIST_NAME = assosiasjoner
    AGGREGATE_HANDLING = Yes
    SUCCESS_ATTR = assosiasjoner.antall
    CALC_CARD = No
    CURVE_BOUNDARY_RULE_PARAM = Default Rule
    LIST_ATTRS_TO_INCLUDE = assosiasjon.XML
    PREDICATES = INTERSECTS
    -> AttributeManager_13
AttributeManager_13
    ATTR_TABLE = SET_TO assosiasjonsId = 220026
    -> assosiasjonXML_6 [ROOT]
Bufferer_2
    OFFSET = 1
    CAP_STYLE = Round
    CORNER_STYLE = Round
    ANGLE = 22.5
    BUFFERED -> SpatialRelator_2 [Supplier]
SpatialRelator_2
    LIST_NAME = assosiasjoner
    AGGREGATE_HANDLING = Yes
    SUCCESS_ATTR = assosiasjoner.antall
    CALC_CARD = No
    CURVE_BOUNDARY_RULE_PARAM = Default Rule
    LIST_ATTRS_TO_INCLUDE = assosiasjon.XML
    PREDICATES = INTERSECTS
    -> AttributeManager_11
AttributeManager_11
    ATTR_TABLE = SET_TO assosiasjonsId = 220027
    -> assosiasjonXML_6 [ROOT]
Bufferer_3
    OFFSET = 1
    CAP_STYLE = Round
    CORNER_STYLE = Round
    ANGLE = 22.5
    BUFFERED -> SpatialRelator_3 [Supplier]
SpatialRelator_3
    LIST_NAME = assosiasjoner
    AGGREGATE_HANDLING = Yes
    SUCCESS_ATTR = assosiasjoner.antall
    CALC_CARD = No
    CURVE_BOUNDARY_RULE_PARAM = Default Rule
    LIST_ATTRS_TO_INCLUDE = assosiasjon.XML
    PREDICATES = INTERSECTS
    -> AttributeManager_10
AttributeManager_10
    ATTR_TABLE = SET_TO assosiasjonsId = 220028
    -> assosiasjonXML_6 [ROOT]
assosiasjonXML_6: XMLTemplater
    ROOT_QUERY_EXPR:
      {if( {fme:get-attribute("endringsflagg.Endringsflagg.typeEndring")}="E") then
      <assosiasjon typeId="{fme:get-attribute("assosiasjonsId")}" operasjon="oppdater">
          {fme:get-list-attribute("assosiasjoner{}.assosiasjon.XML")}
      </assosiasjon>
      else
      <assosiasjon typeId="{fme:get-attribute("assosiasjonsId")}">
          {fme:get-list-attribute("assosiasjoner{}.assosiasjon.XML")}
      </assosiasjon>}
    OUTPUT_XML_HEADER = No
    RESULT_ATTRIBUTE = assosiasjoner.XML
    VISIBLE_QUERY_VALIDATE = Yes
    -> StringReplacer_8
AttributeFilter_Lysmast_-__AttributeValueMapper: Junction
    -> NullAttributeMapper_2
Note: Etablere assosiasjoner basert på geometri: / - Belysningsstrekning til Belysningspunkt / - Belysningspunkt til Lysmast og Lysarmatur / Hardkoda, forbedringspotensliale. Antakelig vha Python-script
StringReplacer_8
    FIND_TEXT = &lt;
    CASE = NO
    REPLACE_TEXT = <
    SRC_ATTRS = assosiasjoner.XML
    REGEXP = NO
    NO_MATCH = _FME_NO_OP_
    -> StringReplacer_9
StringReplacer_9
    FIND_TEXT = &gt;
    CASE = NO
    REPLACE_TEXT = >
    SRC_ATTRS = assosiasjoner.XML
    REGEXP = NO
    NO_MATCH = _FME_NO_OP_
    -> Aggregator
Aggregator
    LIST_NAME = assosiasjoner
    ACCUM_ATTRS_NAME = Merge Incoming Attributes
    ORDERED = No
    MODE = Geometry - Assemble One Level
    SEP = ,
    LIST_ATTRS_TO_INCLUDE = assosiasjoner.XML
    AGGREGATE_TYPE = Homogeneous Collection (If Possible)
    GROUP_BY = tempId
    AGGREGATE -> ListDuplicateRemover
ListDuplicateRemover
    SRC_LIST = assosiasjoner{}.assosiasjoner.XML
    -> NullAttributeMapper_2

Bookmark: Fjerning av eksisterende assosiasjoner
AttributeFilter_3
    ATTR_VALUES = <Empty>,<Missing>,<Null>,<Unfiltered>,Belysningsstrekning,Belysningspunkt,Lysmast,Lysarmatur
    ATTR_NAME = objekttype
    Belysningsstrekning -> AttributeExposer_3
    Belysningspunkt -> AttributeExposer_4
    Belysningspunkt -> AttributeExposer_5
AttributeExposer_3
    ATTR_LIST = assosiertBelysningspunkt{}.xlink_href
    -> ListExploder
ListExploder
    ATTR_CONFLICT_RES = Use List Attribute Values
    LIST_ATTR = assosiertBelysningspunkt{}
    ATTR_ACCUM_MODE = Merge List Attributes
    INDEX_ATTR = _element_index
    ELEMENTS -> AttributeManager_7
AttributeManager_7
    ATTR_TABLE = SET_TO assosiasjonsId = 220026
    -> DuplicateFilter_3
AttributeExposer_4
    ATTR_LIST = assosiertLysmast{}.xlink_href
    -> ListExploder_2
ListExploder_2
    ATTR_CONFLICT_RES = Use List Attribute Values
    LIST_ATTR = assosiertLysmast{}
    ATTR_ACCUM_MODE = Merge List Attributes
    INDEX_ATTR = _element_index
    ELEMENTS -> AttributeManager_6
AttributeManager_6
    ATTR_TABLE = SET_TO assosiasjonsId = 220027
    -> DuplicateFilter_3
AttributeExposer_5
    ATTR_LIST = assosiertLysarmatur{}.xlink_href
    -> ListExploder_3
ListExploder_3
    ATTR_CONFLICT_RES = Use List Attribute Values
    LIST_ATTR = assosiertLysarmatur{}
    ATTR_ACCUM_MODE = Merge List Attributes
    INDEX_ATTR = _element_index
    ELEMENTS -> AttributeManager_5
AttributeManager_5
    ATTR_TABLE = SET_TO assosiasjonsId = 220028
    -> DuplicateFilter_3
DuplicateFilter_3
    INPUT_ORDERED_CHOICE = No
    KEYATTR = xlink_href identifikasjon.Identifikasjon.lokalId
    UNIQUE -> StringSearcher
    UNIQUE -> ListBuilder
StringSearcher
    CASE = no
    STRING_TO_SEARCH = @Value(xlink_href)
    MATCHED_RESULT_ATTR = assosiertId
    REGEXP = [.][0-9]+
    MATCHED -> AttributeTrimmer
AttributeTrimmer
    TRIM_TYPE = Left
    TRIM_TO_NONE = Yes
    TRIM_CHARS = .
    SRC_ATTRS = assosiertId
    -> assosiasjonXML_7 [ROOT] [off]
    -> AttributeManager_8
Note: Lag liste med eksisterende assosiasjoner som skal gjenopprettes senere
AttributeManager_8
    ATTR_TABLE:
      RENAME_SET_VALUE vegObjekt.nvdbId > MorId
      RENAME_SET_VALUE assosiertId > DatterID
      RENAME_SET_VALUE assosiasjonsId > AssosiasjonsID
    -> Assosiasjoner (writer CSV2_2)
Assosiasjoner (writer CSV2_2)
    attributes: MorId int32, DatterID int32, AssosiasjonsID int32
Note: Lager assosiasjons-XML for objektet, til senere bruk
assosiasjonXML_7: XMLTemplater [off]
    ROOT_QUERY_EXPR = <nvdbId>{fme:get-attribute("assosiertId")}</nvdbId>
    OUTPUT_XML_HEADER = No
    RESULT_ATTRIBUTE = assosiasjon.XML
    VISIBLE_QUERY_VALIDATE = Yes
    -> ListBuilder [off]
ListBuilder
    GROUP_BY = assosiasjon.XML vegObjekt.typeId assosiasjonsId vegObjekt.versjon vegObjekt.tempId vegObjekt.nvdbId
    LIST_NAME = assosiasjoner
    LIST_ATTRS_TO_INCLUDE = assosiasjon.XML assosiertId
    -> assosiasjonXML_5 [ROOT] [off]
    -> assosiasjonXML_8 [ROOT]
assosiasjonXML_8: XMLTemplater
    ROOT_QUERY_EXPR = <assosiasjon typeId="{fme:get-attribute("assosiasjonsId")}" operasjon="slett"/>
    OUTPUT_XML_HEADER = No
    RESULT_ATTRIBUTE = assosiasjoner.XML
    VISIBLE_QUERY_VALIDATE = Yes
    -> ListElementCounter
assosiasjonXML_5: XMLTemplater [off]
    ROOT_QUERY_EXPR:
      <assosiasjon typeId="{fme:get-attribute("assosiasjonsId")}" operasjon="slett">
          {fme:get-list-attribute("assosiasjoner{}.assosiasjon.XML")}
      </assosiasjon>
    OUTPUT_XML_HEADER = No
    RESULT_ATTRIBUTE = assosiasjoner.XML
    VISIBLE_QUERY_VALIDATE = Yes
    -> ListElementCounter [off]
ListElementCounter
    CNT_ATTR = assosiasjoner.antall
    LIST_NAME = assosiasjoner{}
    -> StringReplacer_10
StringReplacer_10
    FIND_TEXT = &lt;
    CASE = NO
    REPLACE_TEXT = <
    SRC_ATTRS = assosiasjoner.XML
    REGEXP = NO
    NO_MATCH = _FME_NO_OP_
    -> StringReplacer_11
StringReplacer_11
    FIND_TEXT = &gt;
    CASE = NO
    REPLACE_TEXT = >
    SRC_ATTRS = assosiasjoner.XML
    REGEXP = NO
    NO_MATCH = _FME_NO_OP_
    -> Aggregator_2
Aggregator_2
    LIST_NAME = assosiasjoner
    ACCUM_ATTRS_NAME = Use Attributes From One Feature
    ORDERED = No
    MODE = Geometry - Assemble One Level
    SEP = ,
    LIST_ATTRS_TO_INCLUDE = assosiasjoner.XML
    AGGREGATE_TYPE = Homogeneous Collection (If Possible)
    GROUP_BY = vegObjekt.typeId vegObjekt.versjon vegObjekt.tempId vegObjekt.nvdbId
    COUNT_ATTR = assosiasjoner.antall
    AGGREGATE -> FeatureMerger [SUPPLIER]
FeatureMerger
    REJECT_NULL_MISSING_KEYS = No
    ATTR_ACCUM_MODE = Merge Supplier
    IGNORE_NULLS = No
    ATTR_CONFLICT_RES = Use Supplier
    MERGE_TYPE = Attributes Only
    SUPPLIERS_FIRST = No
    PROCESS_DUPS = No
    JOIN_KEYS = @Value(vegObjekt.nvdbId) @Value(vegObjekt.nvdbId) AUTO
    MERGED -> NullAttributeMapper_2
    UNMERGED_REQUESTOR -> NullAttributeMapper_2 [off]

Bookmark: Opprydding i tekst
StringReplacer_3
    FIND_TEXT = &lt;
    CASE = NO
    REPLACE_TEXT = <
    SRC_ATTRS = vegObjekt.XML
    REGEXP = NO
    NO_MATCH = _FME_NO_OP_
    -> StringReplacer_4
StringReplacer_4
    FIND_TEXT = &gt;
    CASE = NO
    REPLACE_TEXT = >
    SRC_ATTRS = vegObjekt.XML
    REGEXP = NO
    NO_MATCH = _FME_NO_OP_
    -> AttributeRemover_4
AttributeRemover_4
    LIST_ATTRS = egenskaper{}
    -> AttributeManager_4
AttributeManager_4
    NUM_SUBSEQUENT_FEATURES = 0
    NUM_PRIOR_FEATURES = 0
    -> ListBuilder_3

Bookmark: Opprydding
AttributeKeeper_7
    KEEP_ATTRS = endringsflagg.Endringsflagg.typeEndring,fme_feature_type,endringssett.XML
    -> StringReplacer_5
StringReplacer_5
    FIND_TEXT = &lt;
    CASE = NO
    REPLACE_TEXT = <
    SRC_ATTRS = endringssett.XML
    REGEXP = NO
    NO_MATCH = _FME_NO_OP_
    -> StringReplacer_6
StringReplacer_6
    FIND_TEXT = &gt;
    CASE = NO
    REPLACE_TEXT = >
    SRC_ATTRS = endringssett.XML
    REGEXP = NO
    NO_MATCH = _FME_NO_OP_
    -> ListBuilder_4

Bookmark: Opprydding
StringReplacer
    FIND_TEXT = &lt;
    CASE = NO
    REPLACE_TEXT = <
    SRC_ATTRS = endringsliste.XML
    REGEXP = NO
    NO_MATCH = _FME_NO_OP_
    -> StringReplacer_2
StringReplacer_2
    FIND_TEXT = &gt;
    CASE = NO
    REPLACE_TEXT = >
    SRC_ATTRS = endringsliste.XML
    REGEXP = NO
    NO_MATCH = _FME_NO_OP_
    -> XMLFormatter_2
XMLFormatter_2
    XML_ATTR_TEXT = endringsliste.XML
    OUTPUT_ENCODING = utf-8
    LIST_NAME = _xml_error
    WHITESPACE_HANDLING = Preserve all whitespace
    REMOVE_EMPTY_ELEMENT = Yes
    INDENT_SIZE = 1
    REMOVE_ALL_COMMENT = No
    XML_OUTPUT_ATTR = _xml_output
    FORMATTING_CHOICE = Pretty-Print XML
    NAMESPACE_CLEANUP = No
    SCHEMALOC_CLEANUP = No
    TEXT_INDENT = no
    REPLACE_TABS_WITH_SPACES = no
    XML_INPUT_TYPE = Attribute Specifying XML Text
    XML_OUTPUT_TYPE = Attribute
    COLLAPSE_EMPTY_ELEMENT = No
    PASSED -> Sampler [off]
    PASSED -> AttributeRenamer_4

FME custom transformer Vegnettposisjon
Finner prosisjon i vegnettet

Parameters:
- vegkategori = K   # Vegkategori

Input (input)
    -> Counter
Counter
    START = 0
    CNT_ATTR = _count
    SCOPE = Global
    DOMAIN = counter
    -> CoordinateCounter
    -> FeatureMerger [REQUESTOR]
ListBuilder
    GROUP_BY = _coordcount _count ReflinkOID
    LIST_NAME = _list
    LIST_ATTRS_TO_INCLUDE = Measure _element_index
    -> ListRangeExtractor
ListRangeExtractor
    SRC_LIST = _list{}.Measure
    MIN = _min
    MAX = _max
    -> AttributeRemover
AttributeRemover
    LIST_ATTRS = _list{}
    -> AttributeManager
AttributeManager
    ATTR_TABLE:
      SET_TO _posisjon = FME_CONDITIONAL:DEFAULT_VALUE'_FME_NO_OP_'BOOL_OP;OR;COMPOSITE_TEST;<Unused>;TEST @Value(_min) = @Value(_max)'@Value(_min)'FME_NUM_CONDITIONS2___
      SET_TO _fraPosisjon = FME_CONDITIONAL:DEFAULT_VALUE'_FME_NO_OP_'BOOL_OP;OR;COMPOSITE_TEST;<Unused>;TEST @Value(_min) != @Value(_max)'@Value(_min)'FME_NUM_CONDITIONS2___
      SET_TO _tilPosisjon = FME_CONDITIONAL:DEFAULT_VALUE'_FME_NO_OP_'BOOL_OP;OR;COMPOSITE_TEST;<Unused>;TEST @Value(_min) != @Value(_max)'@Value(_max)'FME_NUM_CONDITIONS2___
      REMOVE _max
      REMOVE _min
    -> TestFilter_3
TestFilter_3
    TEST_LIST:
      BOOL_OP,AND,COMPOSITE_TEST,<Unused>,TEST_CLAUSE,"TEST @Value(_coordcount) > 1
      TEST @Value(_posisjon) ATTRIBUTE_HAS_VALUE """"",PunktPosIStrekning
    DEFAULT_VALUE = <UNFILTERED>
    <UNFILTERED> -> FeatureMerger [SUPPLIER]
FeatureMerger
    GEOM_TYPE = Build Polygons
    LIST_NAME = _posList
    CONNECT_Z_MODE = First Wins
    REJECT_NULL_MISSING_KEYS = No
    ATTR_ACCUM_MODE = Merge Supplier
    IGNORE_NULLS = No
    ATTR_CONFLICT_RES = Use Requestor
    LIST_ATTRS_TO_INCLUDE = ReflinkOID _fraPosisjon _posisjon _tilPosisjon
    MERGE_TYPE = Attributes Only
    SUPPLIERS_FIRST = No
    PROCESS_DUPS = Yes
    JOIN_KEYS = @Value(_count) @Value(_count) AUTO
    MERGED -> AttributeManager_3
AttributeManager_3
    ATTR_TABLE = SET_TO lokasjon = FME_CONDITIONAL:DEFAULT_VALUE'_FME_NO_OP_'BOOL_OP;OR;COMPOSITE_TEST;<Unused>;TEST @Value(_posisjon) ATTRIBUTE_HAS_VALUE _FME_BLANK_STRING_'<punkt lenkeId="@Value(ReflinkOID)" posisjon="@Value(_posisjon)"  />'BOOL_OP;AND;COMPOSITE_TEST;<Unused>;TEST @Value(_fraPosisjon) ATTRIBUTE_HAS_VALUE _FME_BLANK_STRING_;TEST @Value(_tilPosisjon) ATTRIBUTE_HAS_VALUE _FME_BLANK_STRING_'<linje lenkeId="@Value(ReflinkOID)" fra="@Value(_fraPosisjon)" til="@Value(_tilPosisjon)" />'FME_NUM_CONDITIONS3___
    -> Output (output)
Output (output)

Bookmark: Finner posisjon i vegnettet
CoordinateCounter
    CNT_ATTR = _coordcount
    -> CoordinateExtractor
Note: Alle knekkpunkt
CoordinateExtractor
    MODE = All Coordinates
    LIST_NAME = _indices
    -> ListExploder
ListExploder
    ATTR_CONFLICT_RES = Use List Attribute Values
    LIST_ATTR = _indices{}
    ATTR_ACCUM_MODE = Merge List Attributes
    INDEX_ATTR = _element_index
    ELEMENTS -> AttributeCreator_2
AttributeCreator_2
    ATTR_TABLE = SET_TO httpReq = https://www.vegvesen.no/nvdb/api/v2/posisjon.xml?nord=@Value(y)&ost=@Value(x)&vegreferanse=$(vegkategori)
    -> HTTPCaller_2
Note: Finner posisjon for representasjonspunktet, med filter på vegkategori
HTTPCaller_2
    TRANSFER_TIMEOUT_LENGTH = 90
    STATUS_CODE_ATTR = _http_status_code
    TARGET_ATTR = _response_body
    SAVE_FILE = Attribute
    HTTP_METHOD = GET
    RESPONSE_HEADER_LIST_ATTR = _headers
    TARGET_URL = @Value(httpReq)
    CONNECTION_TIMEOUT_LENGTH = 60
    VERIFY_SSL_CERTIFICATES = Yes
    USE_COOKIES = No
    FOLLOW_REDIRECTS = Yes
    TARGET_ATTR_ENCODING = auto-detect
    FILE_TYPE = <Auto Detect from HTTP Headers>
    ERROR_ATTR = _error
    -> XMLFlattener_2
    <Rejected> -> AttributeCreator_3
XMLFlattener_2
    FEATURE_TYPES_FORMAT_NAME = XML
    ATTRIBUTE_XML = _response_body
    XML_SOURCE_TYPE = Attribute with XML document
    EMBEDDED_EXPRESSIONS = veglenke
    NEW_ATTRIBUTES = id posisjon
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> TestFilter
Note: Ekstra kontroll på at objektene har fått posisjon. Får en del tilfeller der det ikke gis feil, men bare tomt svar
TestFilter
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_5
    <UNFILTERED> -> AttributeCreator_3
XMLFlattener_5
    FEATURE_TYPES_FORMAT_NAME = XML
    ATTRIBUTE_XML = _response_body
    XML_SOURCE_TYPE = Attribute with XML document
    EMBEDDED_EXPRESSIONS = vegreferanse
    NEW_ATTRIBUTES = fylke kommune kategori status nummer hp meter kortform
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AttributeManager_2
AttributeCreator_3
    ATTR_TABLE = SET_TO httpReq = https://www.vegvesen.no/nvdb/api/v2/posisjon.xml?nord=@Value(y)&ost=@Value(x)
    -> HTTPCaller_3
Note: Finner posisjon for representasjonspunktet, uten filter på vegkategori
HTTPCaller_3
    TRANSFER_TIMEOUT_LENGTH = 90
    STATUS_CODE_ATTR = _http_status_code
    TARGET_ATTR = _response_body
    SAVE_FILE = Attribute
    HTTP_METHOD = GET
    RESPONSE_HEADER_LIST_ATTR = _headers
    TARGET_URL = @Value(httpReq)
    CONNECTION_TIMEOUT_LENGTH = 60
    VERIFY_SSL_CERTIFICATES = Yes
    USE_COOKIES = No
    FOLLOW_REDIRECTS = Yes
    TARGET_ATTR_ENCODING = auto-detect
    FILE_TYPE = <Auto Detect from HTTP Headers>
    ERROR_ATTR = _error
    -> XMLFlattener_4
    <Rejected> -> IngenPosisjon
XMLFlattener_4
    FEATURE_TYPES_FORMAT_NAME = XML
    ATTRIBUTE_XML = _response_body
    XML_SOURCE_TYPE = Attribute with XML document
    EMBEDDED_EXPRESSIONS = veglenke
    NEW_ATTRIBUTES = id posisjon
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> TestFilter_2
Note: Ekstra kontroll på at objektene har fått posisjon. Får en del tilfeller der det ikke gis feil, men bare tomt svar
TestFilter_2
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_3
    <UNFILTERED> -> IngenPosisjon
XMLFlattener_3
    FEATURE_TYPES_FORMAT_NAME = XML
    ATTRIBUTE_XML = _response_body
    XML_SOURCE_TYPE = Attribute with XML document
    EMBEDDED_EXPRESSIONS = vegreferanse
    NEW_ATTRIBUTES = fylke kommune kategori status nummer hp meter kortform
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    -> AnnenVegkategori
    -> AttributeManager_2
AttributeManager_2
    ATTR_TABLE:
      REMOVE httpReq
      REMOVE _error
      REMOVE _headers{}.name
      REMOVE _headers{}.value
      REMOVE _response_body
      REMOVE _http_status_code
      RENAME_SET_VALUE id > ReflinkOID
      RENAME_SET_VALUE posisjon > Measure
      REMOVE fylke
      REMOVE kommune
      RENAME_SET_VALUE kategori > vegident.Vegident.vegkategori
      RENAME_SET_VALUE status > vegident.Vegident.vegstatus
      RENAME_SET_VALUE nummer > vegident.Vegident.vegnummer
      RENAME_SET_VALUE hp > vegparsell.Vegparsell.hovedParsell
      RENAME_SET_VALUE meter > vegparsell.Vegparsell.veglenkeMeterFra
      SET_TO vegparsell.Vegparsell.veglenkeMeterTil = @Value(vegparsell.Vegparsell.veglenkeMeterFra)
      REMOVE kortform
      SET_TO vk = @Value(vegident.Vegident.vegkategori)
    -> ListBuilder
AnnenVegkategori: Inspector
    TACKATTRS = kategori
IngenPosisjon: Inspector
