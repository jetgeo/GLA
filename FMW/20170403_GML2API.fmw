FME workspace 20170403_GML2API.fmw

Parameters:
- SourceDataset_GML = C:\DATA\GitHub\GLA\Data\1902\20170403\Samle_45.gml   # Source Geography Markup Language (GML) File(s)
- omrNvn = 1902   # Område
- wFolder = C:\DATA\GitHub\GLA\Data   # Arbeidsmappe
- vegkategori = K   # Vegkategori
- omr = kommune   # Områdetype
- DakatVersjon = 2.07   # Datakatalogversjon

Readers:
- GML_1: GML from $(SourceDataset_GML)

Writers:
- TEXTLINE_1: TEXTLINE to $(wFolder)\XML\Belysningsdata.xml

Lysarmatur (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedparsell xml_int64, vegreferanse{}.Vegreferanse.veglenkeMeterFra xml_int64, vegreferanse{}.Vegreferanse.veglenkeMeterTil xml_int64, vegreferanse{}.Vegreferanse.referanseretning xml_buffer, vegreferanse{}.Vegreferanse.vegreferanseFraDato xml_date, vegreferanse{}.Vegreferanse.vegreferanseTilDato xml_date, lyskildeType xml_buffer, effekt xml_real64, driftsmerking xml_buffer, driftsattår xml_int64,
      høydeOverVeg xml_real64, antallLyskilderPerArmatur xml_buffer, antallArmaturerIBelysningspkt xml_buffer, inngårINødsystemet xml_buffer, produktnavnArmatur xml_buffer, produsentnavnArmatur xml_buffer, produsentnavnDriver xml_buffer, produsentnavnLyskilde xml_buffer, optikk xml_buffer, konstantLysutbytte xml_buffer, dimming xml_buffer, utystyrsklasse xml_buffer, driftsstrømUdimmet xml_int64, lysflux xml_int64, LEDEffektArmaturTotalt_Test xml_int64, fargetemperatur xml_int64, LEDAntallDioder xml_int64, LEDEffektPerStk_Test xml_real64, avskjermingType xml_buffer, avskjermingMateriale xml_buffer, fargegjengivelsesindeks xml_int64, utskiftbareLyskilder xml_buffer, armaturnummer xml_buffer, kommunikasjonsenhet xml_buffer, eier xml_buffer, eierNavn xml_buffer, vedlikeholdsansvarlig xml_buffer, posisjon xml_geometry, felt xml_buffer, lineærPosisjon{}.LineærPosisjonPunkt.lineærReferanseMetode xml_buffer,
      lineærPosisjon{}.LineærPosisjonPunkt.retning xml_buffer, lineærPosisjon{}.LineærPosisjonPunkt.avstandSide xml_real64, lineærPosisjon{}.LineærPosisjonPunkt.nettverkselement.nilReason xml_buffer, lineærPosisjon{}.LineærPosisjonPunkt.nettverkselement.gml_remoteSchema xml_buffer, lineærPosisjon{}.LineærPosisjonPunkt.nettverkselement.xlink_href xml_buffer, lineærPosisjon{}.LineærPosisjonPunkt.nettverkselement.owns xml_boolean, lineærPosisjon{}.LineærPosisjonPunkt.posisjon xml_real64, assosiertDokumentasjon{}.owns xml_boolean, assosiertDokumentasjon{}.nilReason xml_buffer, assosiertDokumentasjon{}.gml_remoteSchema xml_buffer, assosiertDokumentasjon{}.xlink_href xml_buffer, assosiertKommentar{}.owns xml_boolean, assosiertKommentar{}.nilReason xml_buffer, assosiertKommentar{}.gml_remoteSchema xml_buffer, assosiertKommentar{}.xlink_href xml_buffer
    -> DateFormatter
DateFormatter
    SRCFMT = Unknown - Automatic Detection
    FMT = %Y
    DATE_ATTR = driftsattår
    INVALID_DATE_VALUE = _FME_NO_OP_
    -> org
    -> AttributeManager
org: Inspector
    TACKATTRS = fme_feature_type
AttributeManager
    ATTR_TABLE = SET_TO objekttype = @Value(fme_feature_type)
    -> SchemaMapper
    -> Vegnettposisjon
Note: Posisjon i vegnettet
Vegnettposisjon
    vegkategori = $(vegkategori)
    -> Posisjonert
    -> TestFilter
Note: Skiller melllom nye objekter og objekter som skal endres
TestFilter
    TEST_LIST = BOOL_OP,OR,COMPOSITE_TEST,<Unused>,TEST_CLAUSE,"TEST @Value(endringsflagg.Endringsflagg.typeEndring) != E",Ny
    DEFAULT_VALUE = Endring
    Ny -> SchemaMapper_2
    Endring -> NeighborFinder [BASE]
Posisjonert: Inspector
    TACKATTRS = fme_feature_type
Note: Kobler endirngsobjekter til eksisterende fra NVDB
NeighborFinder
    GROUP_BY = fme_feature_type
    MAX = 10
    K = 1
    CANDIDATES_FIRST = No
    TREAT_POLYGON_AS = Lines
    MODE = Bases and Candidates
    ATTR_ACCUM_MODE = Merge Candidate
    ATTR_CONFLICT_RES = Use Base
    INSERT_VERTEX = No
    MATCHED -> SchemaMapper_2
    UNMATCHED_BASE -> AttributeManager_3
Mapped: Inspector
    TACKATTRS = endringsflagg.Endringsflagg.typeEndring fme_feature_type
AttributeManager_2
    ATTR_TABLE = SET_TO assosiasjoner.antall = 0
    -> Counter_3
Counter_3
    START = 1
    SCOPE = Global
    DOMAIN = counter
    CNT_ATTR = tempId
    -> NullAttributeMapper
NullAttributeMapper
    OTHER_VALUE = 0
    NULL_TREATMENT = Missing
    SOURCE_ATTR_VAL = Null Empty "Missing (Selected Attributes Only)"
    ATTRCHOICE = All Attributes
    -> AttributeExploder
    -> FeatureMerger_5 [REQUESTOR]
Note: Kobler liste med egenskaper til objektet
FeatureMerger_5
    SUPPLIERS_FIRST = No
    JOIN_KEYS = @Value(tempId) @Value(tempId) AUTO
    PROCESS_DUPS = No
    ATTR_ACCUM_MODE = Merge Supplier
    ATTR_CONFLICT_RES = Use Requestor
    IGNORE_NULLS = No
    REJECT_NULL_MISSING_KEYS = No
    MERGE_TYPE = Attributes Only
    MERGED -> AttributeManager_12
Note: Tilpasninger på vegObjektnivå
AttributeManager_12
    ATTR_TABLE:
      SET_TO vegObjekt.typeId = @Value(fme_feature_type)
      SET_TO vegObjekt.tempId = FME_CONDITIONAL:DEFAULT_VALUE'_FME_NO_OP_'BOOL_OP;OR;COMPOSITE_TEST;<Unused>;TEST @Value(endringsflagg.Endringsflagg.typeEndring) = N'@Value(tempId)'FME_NUM_CONDITIONS2___
      SET_TO vegObjekt.nvdbId = FME_CONDITIONAL:DEFAULT_VALUE'_FME_NO_OP_'BOOL_OP;OR;COMPOSITE_TEST;<Unused>;TEST @Value(endringsflagg.Endringsflagg.typeEndring) = E'@Value(identifikasjon.Identifikasjon.lokalId)'FME_NUM_CONDITIONS2___
      SET_TO vegObjekt.versjon = FME_CONDITIONAL:DEFAULT_VALUE'_FME_NO_OP_'BOOL_OP;OR;COMPOSITE_TEST;<Unused>;TEST @Value(endringsflagg.Endringsflagg.typeEndring) = E'@Value(identifikasjon.Identifikasjon.versjonId)'FME_NUM_CONDITIONS2___
    -> assosiasjonXML_2 [ROOT] [off]
    -> NullAttributeMapper_2
Note: Lager assosiasjons-XML for objektet, til senere bruk
assosiasjonXML_2: XMLTemplater
    ROOT_QUERY_EXPR:
      {if( {fme:get-attribute("endringsflagg.Endringsflagg.typeEndring")}="E") then
      <nvdbId>{fme:get-attribute("vegObjekt.nvdbId")}</nvdbId>
      else
      <tempId>-{fme:get-attribute("vegObjekt.tempId")}</tempId>}
    VISIBLE_QUERY_VALIDATE = Yes
    RESULT_ATTRIBUTE = assosiasjon.XML
    OUTPUT_XML_HEADER = No
    -> AttributeFilter
Note: Eksisterende asosiasjoner til objekter som ikke er med i datasettet: / Uberørt av transaksjonen / Men: Kan det bli et problem med ulik stedfesting?
AttributeFilter
    ATTR_VALUES = <Empty>,<Missing>,<Null>,<Unfiltered>,Belysningsstrekning,Belysningspunkt,Lysmast,Lysarmatur
    ATTR_NAME = objekttype
    Belysningsstrekning -> SpatialRelator [Requestor]
    Belysningspunkt -> Bufferer
    Belysningspunkt -> SpatialRelator_2 [Requestor]
    Belysningspunkt -> SpatialRelator_3 [Requestor]
    Lysmast -> AttributeFilter_Lysmast_-__AttributeValueMapper
    Lysmast -> Bufferer_2
    Lysarmatur -> AttributeFilter_Lysmast_-__AttributeValueMapper
    Lysarmatur -> Bufferer_3
Bufferer
    OFFSET = 1
    ANGLE = 22.5
    CAP_STYLE = Round
    CORNER_STYLE = Round
    BUFFERED -> SpatialRelator [Supplier]
SpatialRelator
    CURVE_BOUNDARY_RULE_PARAM = Default Rule
    CALC_CARD = No
    SUCCESS_ATTR = assosiasjoner.antall
    LIST_NAME = assosiasjoner
    PREDICATES = INTERSECTS
    AGGREGATE_HANDLING = Yes
    LIST_ATTRS_TO_INCLUDE = assosiasjon.XML
    -> assosiasjonXML_6 [ROOT]
Note: Etablere assosiasjoner basert på geometri: / - Belysningsstrekning til Belysningspunkt / - Belysningspunkt til Lysmast og Lysarmatur / Hardkoda, forbedringspotensliale. Antakelig vha Python-script
assosiasjonXML_6: XMLTemplater
    ROOT_QUERY_EXPR:
      {if( {fme:get-attribute("endringsflagg.Endringsflagg.typeEndring")}="E") then
      <assosiasjon typeId="220026" operasjon="oppdater">
          {fme:get-list-attribute("assosiasjoner{}.assosiasjon.XML")}
      </assosiasjon>
      else
      <assosiasjon typeId="220026">
          {fme:get-list-attribute("assosiasjoner{}.assosiasjon.XML")}
      </assosiasjon>}
    VISIBLE_QUERY_VALIDATE = Yes
    RESULT_ATTRIBUTE = assosiasjoner.XML
    OUTPUT_XML_HEADER = No
    -> StringReplacer_8
Bufferer_2
    OFFSET = 1
    ANGLE = 22.5
    CAP_STYLE = Round
    CORNER_STYLE = Round
    BUFFERED -> SpatialRelator_2 [Supplier]
SpatialRelator_2
    CURVE_BOUNDARY_RULE_PARAM = Default Rule
    CALC_CARD = No
    SUCCESS_ATTR = assosiasjoner.antall
    LIST_NAME = assosiasjoner
    PREDICATES = INTERSECTS
    AGGREGATE_HANDLING = Yes
    LIST_ATTRS_TO_INCLUDE = assosiasjon.XML
    -> assosiasjonXML_3 [ROOT]
assosiasjonXML_3: XMLTemplater
    ROOT_QUERY_EXPR:
      {if( {fme:get-attribute("endringsflagg.Endringsflagg.typeEndring")}="E") then
      <assosiasjon typeId="220027" operasjon="oppdater">
          {fme:get-list-attribute("assosiasjoner{}.assosiasjon.XML")}
      </assosiasjon>
      else
      <assosiasjon typeId="220027">
          {fme:get-list-attribute("assosiasjoner{}.assosiasjon.XML")}
      </assosiasjon>}
    VISIBLE_QUERY_VALIDATE = Yes
    RESULT_ATTRIBUTE = assosiasjoner.XML
    OUTPUT_XML_HEADER = No
    -> StringReplacer_8
Bufferer_3
    OFFSET = 1
    ANGLE = 22.5
    CAP_STYLE = Round
    CORNER_STYLE = Round
    BUFFERED -> SpatialRelator_3 [Supplier]
SpatialRelator_3
    CURVE_BOUNDARY_RULE_PARAM = Default Rule
    CALC_CARD = No
    SUCCESS_ATTR = assosiasjoner.antall
    LIST_NAME = assosiasjoner
    PREDICATES = INTERSECTS
    AGGREGATE_HANDLING = Yes
    LIST_ATTRS_TO_INCLUDE = assosiasjon.XML
    -> assosiasjonXML_4 [ROOT]
assosiasjonXML_4: XMLTemplater
    ROOT_QUERY_EXPR:
      {if( {fme:get-attribute("endringsflagg.Endringsflagg.typeEndring")}="E") then
      <assosiasjon typeId="220028" operasjon="oppdater">
          {fme:get-list-attribute("assosiasjoner{}.assosiasjon.XML")}
      </assosiasjon>
      else
      <assosiasjon typeId="220028">
          {fme:get-list-attribute("assosiasjoner{}.assosiasjon.XML")}
      </assosiasjon>}
    VISIBLE_QUERY_VALIDATE = Yes
    RESULT_ATTRIBUTE = assosiasjoner.XML
    OUTPUT_XML_HEADER = No
    -> StringReplacer_8
StringReplacer_8
    CASE = NO
    REPLACE_TEXT = <
    REGEXP = NO
    FIND_TEXT = &lt;
    NO_MATCH = _FME_NO_OP_
    SRC_ATTRS = assosiasjoner.XML
    -> StringReplacer_9
StringReplacer_9
    CASE = NO
    REPLACE_TEXT = >
    REGEXP = NO
    FIND_TEXT = &gt;
    NO_MATCH = _FME_NO_OP_
    SRC_ATTRS = assosiasjoner.XML
    -> Aggregator
Aggregator
    SEP = ,
    GROUP_BY = tempId
    ORDERED = No
    MODE = Geometry - Assemble One Level
    ACCUM_ATTRS_NAME = Use Attributes From One Feature
    LIST_NAME = assosiasjoner
    AGGREGATE_TYPE = Homogeneous Collection (If Possible)
    LIST_ATTRS_TO_INCLUDE = assosiasjoner.XML
    AGGREGATE -> NullAttributeMapper_2
AttributeFilter_Lysmast_-__AttributeValueMapper: Junction
    -> NullAttributeMapper_2
NullAttributeMapper_2
    NULL_TREATMENT = New Value
    SOURCE_ATTR_VAL = Null Empty "Missing (Selected Attributes Only)"
    NEW_VALUE = 0
    ATTRLIST = assosiasjoner.antall
    ATTRCHOICE = Selected Attributes
    -> StringFormatter
StringFormatter
    FORMAT = d
    SRC_ATTRS = assosiasjoner.antall
    -> AttributeValueMapper
Note: Geometriegenskap
Note: Håndtering av geometriegenskap må forbedres. Pr nå er denne "hardkoda" i AttributeValueMapper
AttributeValueMapper
    VAL_ATTR = _geometriegenskap
    SRC = fme_feature_type
    LUT = 86,4786,87,4787,88,4788,181,4838
    DIRECTION = Forward (Source To Destination)
    -> vegObjektXML [ROOT]
vegObjektXML: XMLTemplater
    ROOT_QUERY_EXPR:
      {if( fme:has-attribute("vegObjekt.nvdbId")) then
          <vegObjekt typeId="{fme:get-attribute("vegObjekt.typeId")}" nvdbId="{fme:get-attribute("vegObjekt.nvdbId")}" versjon="{fme:get-attribute("vegObjekt.versjon")}">
              <egenskaper>
              {fme:get-list-attribute("egenskaper{}.egenskap.XML")}
              {if( fme:has-attribute("_geometry")) then
              <egenskap typeId="{fme:get-attribute("_geometriegenskap")}" operasjon="oppdater">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}

              <lokasjon operasjon="oppdater">
                  {fme:get-attribute("lokasjon")}
              </lokasjon>
          </vegObjekt>
      else
          <vegObjekt typeId="{fme:get-attribute("vegObjekt.typeId")}" tempId="-{fme:get-attribute("tempId")}">
              <egenskaper>
              {fme:get-list-attribute("egenskaper{}.egenskap.XML")}
              {if( fme:has-attribute("_geometry")) then
              <egenskap typeId="{fme:get-attribute("_geometriegenskap")}">
                  <verdi>{fme:get-attribute("qualityString")}{fme:get-attribute("_geometry")}</verdi>
              </egenskap>
              else ()}
              </egenskaper>
              {if( fme:get-attribute("assosiasjoner.antall")>"0") then
              <assosiasjoner>
                  {fme:get-list-attribute("assosiasjoner{}.assosiasjoner.XML")}
              </assosiasjoner>
              else ()}
              <lokasjon>
                  {fme:get-attribute("lokasjon")}
              </lokasjon>
          </vegObjekt>}
    VISIBLE_QUERY_VALIDATE = Yes
    RESULT_ATTRIBUTE = vegObjekt.XML
    OUTPUT_XML_HEADER = No
    -> StringReplacer_3
ListBuilder_3
    LIST_NAME = vegObjektliste
    GROUP_BY = endringsflagg.Endringsflagg.typeEndring
    -> EndringssettXML [ROOT]
EndringssettXML: XMLTemplater
    ROOT_QUERY_EXPR:
        {if( {fme:get-attribute("endringsflagg.Endringsflagg.typeEndring")}="E") then
        <delvisOppdater>
          <vegObjekter>
          {fme:get-list-attribute("vegObjektliste{}.vegObjekt.XML")}
          </vegObjekter>
        </delvisOppdater>
        else if( {fme:get-attribute("endringsflagg.Endringsflagg.typeEndring")}="N") then
        <registrer>
          <vegObjekter>
          {fme:get-list-attribute("vegObjektliste{}.vegObjekt.XML")}
          </vegObjekter>
        </registrer>
        else ()}
    VISIBLE_QUERY_VALIDATE = Yes
    RESULT_ATTRIBUTE = endringssett.XML
    OUTPUT_XML_HEADER = No
    -> AttributeKeeper_7
ListBuilder_4
    LIST_NAME = endringsliste
    -> TimeStamper
TimeStamper
    TIME_ATTR = _timestamp
    FMT = ^Y-^m-^d
    -> EndringslisteXML [ROOT]
EndringslisteXML: XMLTemplater
    ROOT_QUERY_EXPR:
      <endringssett xmlns="http://nvdb.vegvesen.no/apiskriv/domain/v2" effektDato="{fme:get-attribute("_timestamp")}" datakatalogversjon="$(DakatVersjon)">
      {fme:get-list-attribute("endringsliste{}.endringssett.XML")}
      </endringssett>
    VISIBLE_QUERY_VALIDATE = Yes
    RESULT_ATTRIBUTE = endringsliste.XML
    OUTPUT_XML_HEADER = No
    -> StringReplacer
Sampler
    SAMPLE_TYPE_LONG = Every Nth Feature
    RATE = 1
    GROUP_BY = fme_feature_type
    SAMPLE_MODE = No
    SAMPLED -> AttributeRenamer_4
AttributeRenamer_4
    ATTR_TABLE = RENAME_SET_DEFAULT _xml_output > text_line_data
    -> text_line (writer TEXTLINE_1)
text_line (writer TEXTLINE_1)
    attributes: text_line_data buffer
NVDB: Inspector
    TACKATTRS = fme_feature_type

Bookmark: Eksisterende objekter i NVDB
Note: Mapper objekttypenavn til VOT-ID vha mappingtabell ftMapping / - for å finne aktuellle objekttyper
SchemaMapper
    CSV__IN_FIELD_NAMES = YES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__SKIP_FOOTER = 0
    DATASET = C:\DATA\GitHub\GLA\XSD\glabelysning_ftMapping.csv
    CSV__IN_SEPARATOR = ;
    CSV__SCHEMA_WITH_COL_NAMES = ftid,number,3,0,name,char,18,
    IDXDESTCOL = ftid
    CSV__SKIP_LINES = 1
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    ROW_ID_ATTR = _schemamapper_row_ids
    CSV__DUPLICATE_DELIMS = no
    IDXSOURCECOL = name
    IDXSOURCEATTR = fme_feature_type
    TABLE = CSV
    CSV__ALLOW_SPACES_IN_COLUMN_NAMES = yes
    CSV__GROUP_BY_DATASET = no
    FORMAT = CSV
    CSV__STRIP_QUOTES = yes
    CSV__SCHEMA = number,3,0,char,18,
    CSV__FIELD_NAMES_AFTER_HEADER = no
    CSV_SCAN_MAX_FEATURES = 1000
    MAPPED -> DuplicateFilter
DuplicateFilter
    KEYATTR = fme_feature_type
    INPUT_ORDERED_CHOICE = No
    UNIQUE -> WorkspaceRunner
    UNIQUE -> FeatureReader [INITIATOR]
Note: Eksporterer eksisterende fra NVDB til GML
WorkspaceRunner [off]
    WORKSPACE_PARAMETERS = ftID,@Value(fme_feature_type),omr,$(omr),omrNvn,$(omrNvn),gmlFolder,$(wFolder),dwnlAssObj,Nei
    BLOCKING = Yes
    WORKSPACE_FILE = $(FME_MF_DIR)NVDBAPI2GML_V2_2017.fmw
    SUCCEEDED -> FeatureReader [INITIATOR]
Note: Leser eksisterende NVDB-objekter fra GML
FeatureReader
    GML_IGNORE_APPLICATON_SCHEMA = no
    GML_DISABLE_AUTOMATIC_READER_TYPE_SELECTION = NO
    GML_MAP_PREDEFINED_GML_PROPERTIES = NO
    GML_XML_FRAGMENTS_AS_DOCUMENTS = YES
    GML_MULTI_VALUE_SIMPLE_PROPERTIES_AS_CSV = no
    COMBINE_GEOM = Use Result
    GML_ENFORCE_PATH_CONTINUITY_BY = SNAPPING_END_POINTS
    GML_MAP_EMBEDDED_OBJECTS_AS = ATTRIBUTES
    GML_VALIDATE_DATASET = no
    GML_CONTINUE_ON_GEOM_ERROR = yes
    GML_FEATURE_TYPES_SCHEMA_MODE = XML_SCHEMA
    DATASET = $(wFolder)\$(omr)\$(omrNvn)\@Value(fme_feature_type)\@Value(objekttype).gml
    GML_SKIP_SCHEMA_LOCATION_IN_DATASET = No
    GML_CLIP_TO_ENVELOPE = NO
    GML_CACHE_XSD = yes
    FORMAT = GML
    GML_MAP_ALL_SUBSTITUTABLE_PROPERTIES = YES
    INTERACT = <No Spatial Filter>
    ATTR_ACCUM_MODE = Only Use Result
    GML_FLATTEN_XML_FRAGMENTS = NO
    GML_USE_SEARCH_ENVELOPE = NO
    GML_ADD_GEOMETRIES_AS_XML_FRAGMENTS = NO
    GML_USE_OLD_READER = NO
    GML_DISABLE_XML_NAMESPACE_PROCESSING = NO
    OUTPUT_FEATURES_DISPLAY = Schema and Data Features
    GML_MAP_COMPLEX_PROPERTIES_AS = Nested Attributes
    GML_MAP_GEOMETRY_COLUMNS = YES
    <OTHER> -> AttributeExposer
AttributeExposer
    ATTR_LIST = fme_feature_type,vegreferanse{}.Vegreferanse.vegkategori,identifikasjon.Identifikasjon.lokalId,identifikasjon.Identifikasjon.versjonId,lineærPosisjon{}.LineærPosisjonPunkt.nettverkselement.xlink_href
    -> ListSearcher
Note: Begrenser til objekter på valgt vegkategori
ListSearcher
    INDEX_ATTR = _list_index
    SEARCH_TYPE = First exact match
    LIST_ATTR = vegreferanse{}.Vegreferanse.vegkategori
    ATTR_VALUE = $(vegkategori)
    FOUND -> NVDB
    FOUND -> NeighborFinder [CANDIDATE]

Bookmark: Mapping til Datakatalog-IDer
Note: Setter endringstype = N for de som ikke blir kobla
AttributeManager_3
    ATTR_TABLE = SET_TO endringsflagg.Endringsflagg.typeEndring = N
    -> Endring_uten_eksisterende
    -> SchemaMapper_2
Note: Mapper objekttypenavn til VOT-ID vha mappingtabell ftMapping
SchemaMapper_2
    CSV__IN_FIELD_NAMES = YES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__SKIP_FOOTER = 0
    DATASET = C:\DATA\GitHub\GLA\XSD\glabelysning_ftMapping.csv
    CSV__IN_SEPARATOR = ;
    CSV__SCHEMA_WITH_COL_NAMES = ftid,number,3,0,name,char,18,
    IDXDESTCOL = ftid
    CSV__SKIP_LINES = 1
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    ROW_ID_ATTR = _schemamapper_row_ids
    CSV__DUPLICATE_DELIMS = no
    IDXSOURCECOL = name
    IDXSOURCEATTR = fme_feature_type
    TABLE = CSV
    CSV__ALLOW_SPACES_IN_COLUMN_NAMES = yes
    CSV__GROUP_BY_DATASET = no
    FORMAT = CSV
    CSV__STRIP_QUOTES = yes
    CSV__SCHEMA = number,3,0,char,18,
    CSV__FIELD_NAMES_AFTER_HEADER = no
    CSV_SCAN_MAX_FEATURES = 1000
    MAPPED -> AttributeExposer_2
AttributeExposer_2
    ATTR_LIST = fme_feature_type
    -> SchemaMapper_3
Note: Mapper egenskapsnavn til ET-ID vha mappingtabell ptMapping
SchemaMapper_3
    CSV__IN_FIELD_NAMES = YES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__SKIP_FOOTER = 0
    DATASET = C:\DATA\GitHub\GLA\XSD\glabelysning_ptMapping.csv
    CSV__IN_SEPARATOR = ;
    CSV__SCHEMA_WITH_COL_NAMES = ft_attr,char,17,,ftid,number,4,0,ptid,number,6,0,name,char,43,
    IDXDESTCOL = ""
    CSV__SKIP_LINES = 1
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    ROW_ID_ATTR = _schemamapper_row_ids
    CSV__DUPLICATE_DELIMS = no
    IDXSOURCECOL = ""
    IDXSOURCEATTR = fme_feature_type
    TABLE = CSV
    CSV__ALLOW_SPACES_IN_COLUMN_NAMES = yes
    CSV__GROUP_BY_DATASET = no
    MATCH_ATTRS = ft_attr ftid
    MAP_ATTRS = name ptid $(FME_ASC_16)
    FORMAT = CSV
    CSV__STRIP_QUOTES = yes
    CSV__SCHEMA = char,17,,number,4,0,number,6,0,char,43,
    CSV__FIELD_NAMES_AFTER_HEADER = no
    CSV_SCAN_MAX_FEATURES = 1000
    MAPPED -> SchemaMapper_4
Note: Oversetter tillatte verdier til NVDB-tekstverdier
SchemaMapper_4
    CSV__IN_FIELD_NAMES = YES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    CSV__SKIP_FOOTER = 0
    DATASET = C:\DATA\GitHub\GLA\XSD\glabelysning_enMapping.csv
    CSV__IN_SEPARATOR = ;
    CSV__SCHEMA_WITH_COL_NAMES = ptid,number,6,0,enid,number,6,0,name,char,29,,fullname,char,34,
    IDXDESTCOL = ""
    CSV__SKIP_LINES = 1
    IDXDESTATTR = fme_feature_type
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    ROW_ID_ATTR = _schemamapper_row_ids
    CSV__DUPLICATE_DELIMS = no
    IDXSOURCECOL = ""
    IDXSOURCEATTR = fme_feature_type
    TABLE = CSV
    CSV__ALLOW_SPACES_IN_COLUMN_NAMES = yes
    CSV__GROUP_BY_DATASET = no
    MATCH_ATTRS = ptid name
    MAP_ATTRS = name ptid fullname
    FORMAT = CSV
    CSV__STRIP_QUOTES = yes
    CSV__SCHEMA = number,6,0,number,6,0,char,29,,char,34,
    CSV__FIELD_NAMES_AFTER_HEADER = no
    CSV_SCAN_MAX_FEATURES = 1000
    MAPPED -> AttributeExposer_4
    MAPPED -> CoordinateRounder
AttributeExposer_4 [off]
    ATTR_LIST = 1832
    -> AttributeManager_13
AttributeManager_13 [off]
    ATTR_TABLE = SET_TO 1832 = FME_CONDITIONAL:DEFAULT_VALUE'FME_NULL_VALUE'BOOL_OP;OR;COMPOSITE_TEST;<Unused>;TEST @Value(1832) = nei;TEST @Value(1832) = Nei'Nei'BOOL_OP;OR;COMPOSITE_TEST;<Unused>;TEST @Value(1832) = ja;TEST @Value(1832) = Ja'Ja'FME_NUM_CONDITIONS3___
    -> CoordinateRounder [off]
Endring_uten_eksisterende: Inspector
    TACKATTRS = fme_feature_type

Bookmark: Lager geometristreng
CoordinateRounder
    XPREC = 3
    YPREC = 3
    ZPREC = 3
    ROUNDED -> CoordinateConcatenator
CoordinateConcatenator
    COORD_DELIM = ,
    ELEMENT_DELIM = " "
    COORD_ATTR = _coordinates
    COORDINATES_TO_INCLUDE_DIS = X Y Z
    PRECISION = No
    -> StringReplacer_7
StringReplacer_7
    CASE = NO
    REGEXP = NO
    FIND_TEXT = " -99999"
    NO_MATCH = _FME_NO_OP_
    SRC_ATTRS = _coordinates
    -> GeometryFilter
GeometryFilter
    BREAK_AGG = No
    GEOM_PORT_NAMES = Point Line
    POINT -> StringConcatenator_2
    LINE -> StringConcatenator
StringConcatenator_2
    VAL_ATTR = _geometry
    ACTION = Create New Attribute
    PARM_LINE = POINT(@Value(_coordinates))
    -> StringConcatenator_2_OUTPUT_-__PythonCaller
StringConcatenator
    VAL_ATTR = _geometry
    ACTION = Create New Attribute
    PARM_LINE = LINESTRING(@Value(_coordinates))
    -> StringConcatenator_2_OUTPUT_-__PythonCaller
StringConcatenator_2_OUTPUT_-__PythonCaller: Junction
    -> PythonCaller
Note: Kvalitetsstreng
PythonCaller
    NEW_ATTRIBUTES = qualityString
    PYTHONSOURCE:
      import fmeobjects
      # Template Function interface:

      def setQuality(feature):
          qs=""
          qm = feature.getAttribute('kvalitet.Posisjonskvalitet.målemetode')
          qms=str(qm)
          if qms <> "None":
              qs="målemetode="+qms

          qm = feature.getAttribute('kvalitet.Posisjonskvalitet.nøyaktighet')
          qms=str(qm)
          if qms <> "None":
              qs=qs+"; nøyaktighet="+qms

          qm = feature.getAttribute('kvalitet.Posisjonskvalitet.synbarhet')
          qms=str(qm)
          if qms <> "None":
              qs=qs+"; synbarhet="+qms

          qm = feature.getAttribute('kvalitet.Posisjonskvalitet.målemetodeHøyde')
          qms=str(qm)
          if qms <> "None":
              qs=qs+"; målemetodeHøyde="+qms

          qm = feature.getAttribute('kvalitet.Posisjonskvalitet.nøyaktighetHøyde')
          qms=str(qm)
          if qms <> "None":
              qs=qs+"; nøyaktighetHøyde="+qms

          if qs <> "":
              feature.setAttribute('qualityString', qs+'; ')
    PYTHONSYMBOL = setQuality
    -> Mapped
    -> AttributeManager_2

Bookmark: Liste med egenskaper
AttributeExploder
    ATTR_NAME_LABEL = _attr_name
    KEEP_ATTRIBUTES = Yes
    ATTR_VALUE_LABEL = _attr_value
    EXPLODING_TYPE = Features
    KEEP_GEOMETRY = No
    -> AttributeKeeper_5
AttributeKeeper_5
    KEEP_ATTRS = endringsflagg.Endringsflagg.typeEndring,_attr_value,tempId,_attr_name
    -> AttributeValidator
AttributeValidator
    TABLE = _attr_name;TYPE;NUM
    PASSED -> AttributeManager_9
AttributeManager_9
    ATTR_TABLE:
      RENAME_SET_VALUE _attr_name > egenskap.typeId
      RENAME_SET_VALUE _attr_value > egenskap.verdi
      SET_TO egenskap.operasjon = FME_CONDITIONAL:DEFAULT_VALUE'_FME_NO_OP_'BOOL_OP;OR;COMPOSITE_TEST;<Unused>;TEST @Value(endringsflagg.Endringsflagg.typeEndring) = E'oppdater'FME_NUM_CONDITIONS2___
    -> egenskapXML [ROOT]
egenskapXML: XMLTemplater
    ROOT_QUERY_EXPR:
      {if( fme:has-attribute("egenskap.operasjon")) then
      <egenskap typeId="{fme:get-attribute("egenskap.typeId")}" operasjon="{fme:get-attribute("egenskap.operasjon")}">
          <verdi>{fme:get-attribute("egenskap.verdi")}</verdi>
      </egenskap>
      else
      <egenskap typeId="{fme:get-attribute("egenskap.typeId")}">
          <verdi>{fme:get-attribute("egenskap.verdi")}</verdi>
      </egenskap>}
    VISIBLE_QUERY_VALIDATE = Yes
    RESULT_ATTRIBUTE = egenskap.XML
    OUTPUT_XML_HEADER = No
    -> ListBuilder_2
ListBuilder_2
    LIST_NAME = egenskaper
    GROUP_BY = tempId
    -> FeatureMerger_5 [SUPPLIER]

Bookmark: Opprydding i tekst
StringReplacer_3
    CASE = NO
    REPLACE_TEXT = <
    REGEXP = NO
    FIND_TEXT = &lt;
    NO_MATCH = _FME_NO_OP_
    SRC_ATTRS = vegObjekt.XML
    -> StringReplacer_4
StringReplacer_4
    CASE = NO
    REPLACE_TEXT = >
    REGEXP = NO
    FIND_TEXT = &gt;
    NO_MATCH = _FME_NO_OP_
    SRC_ATTRS = vegObjekt.XML
    -> AttributeRemover_4
AttributeRemover_4
    LIST_ATTRS = egenskaper{}
    -> AttributeManager_4
AttributeManager_4
    NUM_PRIOR_FEATURES = 0
    NUM_SUBSEQUENT_FEATURES = 0
    -> ListBuilder_3

Bookmark: Opprydding
AttributeKeeper_7
    KEEP_ATTRS = endringsflagg.Endringsflagg.typeEndring,fme_feature_type,endringssett.XML
    -> StringReplacer_5
StringReplacer_5
    CASE = NO
    REPLACE_TEXT = <
    REGEXP = NO
    FIND_TEXT = &lt;
    NO_MATCH = _FME_NO_OP_
    SRC_ATTRS = endringssett.XML
    -> StringReplacer_6
StringReplacer_6
    CASE = NO
    REPLACE_TEXT = >
    REGEXP = NO
    FIND_TEXT = &gt;
    NO_MATCH = _FME_NO_OP_
    SRC_ATTRS = endringssett.XML
    -> ListBuilder_4

Bookmark: Opprydding
StringReplacer
    CASE = NO
    REPLACE_TEXT = <
    REGEXP = NO
    FIND_TEXT = &lt;
    NO_MATCH = _FME_NO_OP_
    SRC_ATTRS = endringsliste.XML
    -> StringReplacer_2
StringReplacer_2
    CASE = NO
    REPLACE_TEXT = >
    REGEXP = NO
    FIND_TEXT = &gt;
    NO_MATCH = _FME_NO_OP_
    SRC_ATTRS = endringsliste.XML
    -> XMLFormatter_2
XMLFormatter_2
    OUTPUT_ENCODING = utf-8
    NAMESPACE_CLEANUP = No
    XML_OUTPUT_TYPE = Attribute
    FORMATTING_CHOICE = Pretty-Print XML
    INDENT_SIZE = 1
    SCHEMALOC_CLEANUP = No
    TEXT_INDENT = no
    XML_ATTR_TEXT = endringsliste.XML
    XML_OUTPUT_ATTR = _xml_output
    XML_INPUT_TYPE = Attribute Specifying XML Text
    LIST_NAME = _xml_error
    WHITESPACE_HANDLING = Preserve all whitespace
    REPLACE_TABS_WITH_SPACES = no
    REMOVE_EMPTY_ELEMENT = Yes
    COLLAPSE_EMPTY_ELEMENT = No
    REMOVE_ALL_COMMENT = No
    PASSED -> Sampler [off]
    PASSED -> AttributeRenamer_4

FME custom transformer Vegnettposisjon
Finner prosisjon i vegnettet

Parameters:
- vegkategori = K   # Vegkategori

Input (input)
    -> Counter
Counter
    START = 0
    SCOPE = Global
    DOMAIN = counter
    CNT_ATTR = _count
    -> CoordinateCounter
    -> FeatureMerger [REQUESTOR]
ListBuilder
    LIST_NAME = _list
    GROUP_BY = _coordcount _count ReflinkOID
    LIST_ATTRS_TO_INCLUDE = Measure _element_index
    -> ListRangeExtractor
ListRangeExtractor
    MIN = _min
    SRC_LIST = _list{}.Measure
    MAX = _max
    -> AttributeRemover
AttributeRemover
    LIST_ATTRS = _list{}
    -> AttributeManager
AttributeManager
    ATTR_TABLE:
      SET_TO _posisjon = FME_CONDITIONAL:DEFAULT_VALUE'_FME_NO_OP_'BOOL_OP;OR;COMPOSITE_TEST;<Unused>;TEST @Value(_min) = @Value(_max)'@Value(_min)'FME_NUM_CONDITIONS2___
      SET_TO _fraPosisjon = FME_CONDITIONAL:DEFAULT_VALUE'_FME_NO_OP_'BOOL_OP;OR;COMPOSITE_TEST;<Unused>;TEST @Value(_min) != @Value(_max)'@Value(_min)'FME_NUM_CONDITIONS2___
      SET_TO _tilPosisjon = FME_CONDITIONAL:DEFAULT_VALUE'_FME_NO_OP_'BOOL_OP;OR;COMPOSITE_TEST;<Unused>;TEST @Value(_min) != @Value(_max)'@Value(_max)'FME_NUM_CONDITIONS2___
      REMOVE _max
      REMOVE _min
    -> TestFilter_3
TestFilter_3
    TEST_LIST:
      BOOL_OP,AND,COMPOSITE_TEST,<Unused>,TEST_CLAUSE,"TEST @Value(_coordcount) > 1
      TEST @Value(_posisjon) ATTRIBUTE_HAS_VALUE """"",PunktPosIStrekning
    DEFAULT_VALUE = <UNFILTERED>
    <UNFILTERED> -> FeatureMerger [SUPPLIER]
FeatureMerger
    SUPPLIERS_FIRST = No
    JOIN_KEYS = @Value(_count) @Value(_count) AUTO
    GEOM_TYPE = Build Polygons
    PROCESS_DUPS = Yes
    ATTR_ACCUM_MODE = Merge Supplier
    ATTR_CONFLICT_RES = Use Requestor
    IGNORE_NULLS = No
    REJECT_NULL_MISSING_KEYS = No
    LIST_NAME = _posList
    MERGE_TYPE = Attributes Only
    CONNECT_Z_MODE = First Wins
    LIST_ATTRS_TO_INCLUDE = ReflinkOID _fraPosisjon _posisjon _tilPosisjon
    MERGED -> AttributeManager_3
AttributeManager_3
    ATTR_TABLE = SET_TO lokasjon = FME_CONDITIONAL:DEFAULT_VALUE'_FME_NO_OP_'BOOL_OP;OR;COMPOSITE_TEST;<Unused>;TEST @Value(_posisjon) ATTRIBUTE_HAS_VALUE _FME_BLANK_STRING_'<punkt lenkeId="@Value(ReflinkOID)" posisjon="@Value(_posisjon)"  />'BOOL_OP;AND;COMPOSITE_TEST;<Unused>;TEST @Value(_fraPosisjon) ATTRIBUTE_HAS_VALUE _FME_BLANK_STRING_;TEST @Value(_tilPosisjon) ATTRIBUTE_HAS_VALUE _FME_BLANK_STRING_'<linje lenkeId="@Value(ReflinkOID)" fra="@Value(_fraPosisjon)" til="@Value(_tilPosisjon)" />'FME_NUM_CONDITIONS3___
    -> Output (output)
Output (output)

Bookmark: Finner posisjon i vegnettet
CoordinateCounter
    CNT_ATTR = _coordcount
    -> CoordinateExtractor
Note: Alle knekkpunkt
CoordinateExtractor
    LIST_NAME = _indices
    MODE = All Coordinates
    -> ListExploder
ListExploder
    ATTR_ACCUM_MODE = Merge List Attributes
    INDEX_ATTR = _element_index
    ATTR_CONFLICT_RES = Use List Attribute Values
    LIST_ATTR = _indices{}
    ELEMENTS -> AttributeCreator_2
AttributeCreator_2
    ATTR_TABLE = SET_TO httpReq = https://www.vegvesen.no/nvdb/api/v2/posisjon.xml?nord=@Value(y)&ost=@Value(x)&vegreferanse=$(vegkategori)
    -> HTTPCaller_2
Note: Finner posisjon for representasjonspunktet, med filter på vegkategori
HTTPCaller_2
    FOLLOW_REDIRECTS = Yes
    CONNECTION_TIMEOUT_LENGTH = 60
    VERIFY_SSL_CERTIFICATES = Yes
    RESPONSE_HEADER_LIST_ATTR = _headers
    TARGET_ATTR = _response_body
    USE_COOKIES = No
    TARGET_ATTR_ENCODING = auto-detect
    STATUS_CODE_ATTR = _http_status_code
    ERROR_ATTR = _error
    SAVE_FILE = Attribute
    HTTP_METHOD = GET
    TRANSFER_TIMEOUT_LENGTH = 90
    TARGET_URL = @Value(httpReq)
    FILE_TYPE = <Auto Detect from HTTP Headers>
    -> XMLFlattener_2
    <Rejected> -> AttributeCreator_3
XMLFlattener_2
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = veglenke
    XML_SOURCE_TYPE = Attribute with XML document
    ATTRIBUTE_XML = _response_body
    FEATURE_TYPES_FORMAT_NAME = XML
    NEW_ATTRIBUTES = id posisjon
    -> TestFilter
Note: Ekstra kontroll på at objektene har fått posisjon. Får en del tilfeller der det ikke gis feil, men bare tomt svar
TestFilter
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_5
    <UNFILTERED> -> AttributeCreator_3
XMLFlattener_5
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = vegreferanse
    XML_SOURCE_TYPE = Attribute with XML document
    ATTRIBUTE_XML = _response_body
    FEATURE_TYPES_FORMAT_NAME = XML
    NEW_ATTRIBUTES = fylke kommune kategori status nummer hp meter kortform
    -> AttributeManager_2
AttributeCreator_3
    ATTR_TABLE = SET_TO httpReq = https://www.vegvesen.no/nvdb/api/v2/posisjon.xml?nord=@Value(y)&ost=@Value(x)
    -> HTTPCaller_3
Note: Finner posisjon for representasjonspunktet, uten filter på vegkategori
HTTPCaller_3
    FOLLOW_REDIRECTS = Yes
    CONNECTION_TIMEOUT_LENGTH = 60
    VERIFY_SSL_CERTIFICATES = Yes
    RESPONSE_HEADER_LIST_ATTR = _headers
    TARGET_ATTR = _response_body
    USE_COOKIES = No
    TARGET_ATTR_ENCODING = auto-detect
    STATUS_CODE_ATTR = _http_status_code
    ERROR_ATTR = _error
    SAVE_FILE = Attribute
    HTTP_METHOD = GET
    TRANSFER_TIMEOUT_LENGTH = 90
    TARGET_URL = @Value(httpReq)
    FILE_TYPE = <Auto Detect from HTTP Headers>
    -> XMLFlattener_4
    <Rejected> -> IngenPosisjon
XMLFlattener_4
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = veglenke
    XML_SOURCE_TYPE = Attribute with XML document
    ATTRIBUTE_XML = _response_body
    FEATURE_TYPES_FORMAT_NAME = XML
    NEW_ATTRIBUTES = id posisjon
    -> TestFilter_2
Note: Ekstra kontroll på at objektene har fått posisjon. Får en del tilfeller der det ikke gis feil, men bare tomt svar
TestFilter_2
    TEST_LIST:
      BOOL_OP,AND,COMPOSITE_TEST,<Unused>,TEST_CLAUSE,"TEST @Value(posisjon) ATTRIBUTE_HAS_VALUE """"
      TEST @Value(id) ATTRIBUTE_HAS_VALUE """"",HarPosisjon
    DEFAULT_VALUE = <UNFILTERED>
    HarPosisjon -> XMLFlattener_3
    <UNFILTERED> -> IngenPosisjon
XMLFlattener_3
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = vegreferanse
    XML_SOURCE_TYPE = Attribute with XML document
    ATTRIBUTE_XML = _response_body
    FEATURE_TYPES_FORMAT_NAME = XML
    NEW_ATTRIBUTES = fylke kommune kategori status nummer hp meter kortform
    -> AnnenVegkategori
    -> AttributeManager_2
AttributeManager_2
    ATTR_TABLE:
      REMOVE httpReq
      REMOVE _error
      REMOVE _headers{}.name
      REMOVE _headers{}.value
      REMOVE _response_body
      REMOVE _http_status_code
      RENAME_SET_VALUE id > ReflinkOID
      RENAME_SET_VALUE posisjon > Measure
      REMOVE fylke
      REMOVE kommune
      RENAME_SET_VALUE kategori > vegident.Vegident.vegkategori
      RENAME_SET_VALUE status > vegident.Vegident.vegstatus
      RENAME_SET_VALUE nummer > vegident.Vegident.vegnummer
      RENAME_SET_VALUE hp > vegparsell.Vegparsell.hovedParsell
      RENAME_SET_VALUE meter > vegparsell.Vegparsell.veglenkeMeterFra
      SET_TO vegparsell.Vegparsell.veglenkeMeterTil = @Value(vegparsell.Vegparsell.veglenkeMeterFra)
      REMOVE kortform
      SET_TO vk = @Value(vegident.Vegident.vegkategori)
    -> ListBuilder
AnnenVegkategori: Inspector
    TACKATTRS = kategori
IngenPosisjon: Inspector
